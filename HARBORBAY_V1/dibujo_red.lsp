(setq *error* (lambda (msg) (if msg (princ (strcat "\nError: " msg)))))
(setvar "OSMODE" 0)
(command "_.UNDO" "BEGIN")
(command "-LAYER" "N" "Niveles" "C" "8" "" "")
(command "-LAYER" "N" "Switches" "C" "6" "" "")
(command "-LAYER" "N" "Textos" "C" "7" "" "")
(command "-LAYER" "N" "Cables_UTP" "C" "5" "" "")
(command "-LAYER" "N" "Fibra_WiFi" "C" "2" "" "")
(command "-LAYER" "N" "Fibra_Telefonia" "C" "2" "" "")
(command "-LAYER" "N" "Fibra_IPTV" "C" "2" "" "")
(command "-LAYER" "N" "Fibra_CCTV" "C" "2" "" "")
(command "-LAYER" "N" "Fibra_Data" "C" "2" "" "")
(command "-LAYER" "N" "APs" "C" "3" "" "")
(command "-LAYER" "N" "Telefonos" "C" "4" "" "")
(command "-LAYER" "N" "TVs" "C" "5" "" "")
(command "-LAYER" "N" "Camaras" "C" "1" "" "")
(command "-LAYER" "N" "Datos" "C" "1" "" "")
(command "-LAYER" "N" "UPS" "C" "1" "" "")
(command "-LAYER" "N" "Estadisticas" "C" "7" "" "")

; === DIBUJAR TORRE: MDF ===
(command "-LAYER" "S" "Textos" "")
(command "-COLOR" "7")
(command "-TEXT" "S" "Standard" "J" "C" (list 100 150) 25 0 "MDF")
(command "-LAYER" "S" "UPS" "")
(command "-COLOR" "1")
(command "_.PLINE" (list 150 150) (list 230 150) (list 230 210) (list 150 210) "C")
(command "-LAYER" "S" "Textos" "")
(command "-COLOR" "7")
(command "-TEXT" "S" "Standard" "J" "C" (list 175 175) 15 0 "UPS")
(command "-LAYER" "S" "Textos" "")
(command "-COLOR" "7")
(command "-TEXT" "S" "Standard" "J" "C" (list 155 130) 10 0 "ALIMENTACION")
(command "-LAYER" "S" "Switches" "")
(command "-COLOR" "6")
(command "_.PLINE" (list 150 240) (list 300 240) (list 300 280) (list 150 280) "C")
(command "-LAYER" "S" "Textos" "")
(command "-COLOR" "7")
(command "-TEXT" "S" "Standard" "J" "MC" (list 225.0 260.0) 8 0 "SW-CCTV (DS-3E3728F)")
(command "-LAYER" "S" "Switches" "")
(command "-COLOR" "6")
(command "_.PLINE" (list 150 340) (list 300 340) (list 300 380) (list 150 380) "C")
(command "-LAYER" "S" "Textos" "")
(command "-COLOR" "7")
(command "-TEXT" "S" "Standard" "J" "MC" (list 225.0 360.0) 8 0 "SW-DATA (Meraki MS225)")
(command "-LAYER" "S" "Switches" "")
(command "-COLOR" "6")
(command "_.PLINE" (list 150 440) (list 300 440) (list 300 480) (list 150 480) "C")
(command "-LAYER" "S" "Textos" "")
(command "-COLOR" "7")
(command "-TEXT" "S" "Standard" "J" "MC" (list 225.0 460.0) 8 0 "SW-IPTV (RG-NBS6002)")
(command "-LAYER" "S" "Switches" "")
(command "-COLOR" "6")
(command "_.PLINE" (list 150 540) (list 300 540) (list 300 580) (list 150 580) "C")
(command "-LAYER" "S" "Textos" "")
(command "-COLOR" "7")
(command "-TEXT" "S" "Standard" "J" "MC" (list 225.0 560.0) 8 0 "SW-TEL (Meraki MS225)")
(command "-LAYER" "S" "Switches" "")
(command "-COLOR" "6")
(command "_.PLINE" (list 150 640) (list 300 640) (list 300 680) (list 150 680) "C")
(command "-LAYER" "S" "Textos" "")
(command "-COLOR" "7")
(command "-TEXT" "S" "Standard" "J" "MC" (list 225.0 660.0) 8 0 "SW-WIFI (Meraki MS225)")

; === DIBUJAR TORRE: IDF1 ===
(command "-LAYER" "S" "Textos" "")
(command "-COLOR" "7")
(command "-TEXT" "S" "Standard" "J" "C" (list 1150 150) 25 0 "IDF1")
(command "-LAYER" "S" "Switches" "")
(command "-COLOR" "6")
(command "_.PLINE" (list 1200 150) (list 1350 150) (list 1350 190) (list 1200 190) "C")
(command "-LAYER" "S" "Textos" "")
(command "-COLOR" "7")
(command "-TEXT" "S" "Standard" "J" "MC" (list 1275.0 170.0) 8 0 "SW-CCTV (DS-3E3728F)")
(command "-LAYER" "S" "Switches" "")
(command "-COLOR" "6")
(command "_.PLINE" (list 1200 250) (list 1350 250) (list 1350 290) (list 1200 290) "C")
(command "-LAYER" "S" "Textos" "")
(command "-COLOR" "7")
(command "-TEXT" "S" "Standard" "J" "MC" (list 1275.0 270.0) 8 0 "SW-DATA (Meraki MS225)")
(command "-LAYER" "S" "Switches" "")
(command "-COLOR" "6")
(command "_.PLINE" (list 1200 350) (list 1350 350) (list 1350 390) (list 1200 390) "C")
(command "-LAYER" "S" "Textos" "")
(command "-COLOR" "7")
(command "-TEXT" "S" "Standard" "J" "MC" (list 1275.0 370.0) 8 0 "SW-IPTV (RG-NBS6002)")
(command "-LAYER" "S" "Switches" "")
(command "-COLOR" "6")
(command "_.PLINE" (list 1200 450) (list 1350 450) (list 1350 490) (list 1200 490) "C")
(command "-LAYER" "S" "Textos" "")
(command "-COLOR" "7")
(command "-TEXT" "S" "Standard" "J" "MC" (list 1275.0 470.0) 8 0 "SW-TEL (Meraki MS225)")
(command "-LAYER" "S" "Switches" "")
(command "-COLOR" "6")
(command "_.PLINE" (list 1200 550) (list 1350 550) (list 1350 590) (list 1200 590) "C")
(command "-LAYER" "S" "Textos" "")
(command "-COLOR" "7")
(command "-TEXT" "S" "Standard" "J" "MC" (list 1275.0 570.0) 8 0 "SW-WIFI (Meraki MS225)")
(command "-LAYER" "S" "APs" "")
(command "-COLOR" "3")
(command "_.PLINE" (list 1290.0 840) (list 1310.0 840) (list 1300 865) (list 1290.0 840) "")
(command "_.CIRCLE" (list 1300 865) 10)
(command "_.CIRCLE" (list 1300 865) 21.25)
(command "_.CIRCLE" (list 1300 865) 30)
(command "-LAYER" "S" "Textos" "")
(command "-COLOR" "7")
(command "-TEXT" "S" "Standard" "J" "C" (list 1270 855) 10 0 "2xAP")
(command "-LAYER" "S" "Telefonos" "")
(command "-COLOR" "4")
(command "_.PLINE" (list 1290.0 920) (list 1310.0 920) (list 1310.0 950) (list 1290.0 950) "C")
(command "_.CIRCLE" (list 1300 957) 5)
(command "-LAYER" "S" "Textos" "")
(command "-COLOR" "7")
(command "-TEXT" "S" "Standard" "J" "C" (list 1270 935) 10 0 "1xTEL")
(command "-LAYER" "S" "TVs" "")
(command "-COLOR" "5")
(command "_.PLINE" (list 1280.0 1000) (list 1320.0 1000) (list 1320.0 1025) (list 1280.0 1025) "C")
(command "_.PLINE" (list 1290.0 1000) (list 1310.0 1000) (list 1300 990) (list 1290.0 1000) "")
(command "-LAYER" "S" "Textos" "")
(command "-COLOR" "7")
(command "-TEXT" "S" "Standard" "J" "C" (list 1270 1015) 10 0 "3xTV")
(command "-LAYER" "S" "APs" "")
(command "-COLOR" "3")
(command "_.PLINE" (list 1290.0 2160) (list 1310.0 2160) (list 1300 2185) (list 1290.0 2160) "")
(command "_.CIRCLE" (list 1300 2185) 10)
(command "_.CIRCLE" (list 1300 2185) 21.25)
(command "_.CIRCLE" (list 1300 2185) 30)
(command "-LAYER" "S" "Textos" "")
(command "-COLOR" "7")
(command "-TEXT" "S" "Standard" "J" "C" (list 1270 2175) 10 0 "11xAP")
(command "-LAYER" "S" "Telefonos" "")
(command "-COLOR" "4")
(command "_.PLINE" (list 1290.0 2240) (list 1310.0 2240) (list 1310.0 2270) (list 1290.0 2270) "C")
(command "_.CIRCLE" (list 1300 2277) 5)
(command "-LAYER" "S" "Textos" "")
(command "-COLOR" "7")
(command "-TEXT" "S" "Standard" "J" "C" (list 1270 2255) 10 0 "5xTEL")
(command "-LAYER" "S" "TVs" "")
(command "-COLOR" "5")
(command "_.PLINE" (list 1280.0 2320) (list 1320.0 2320) (list 1320.0 2345) (list 1280.0 2345) "C")
(command "_.PLINE" (list 1290.0 2320) (list 1310.0 2320) (list 1300 2310) (list 1290.0 2320) "")
(command "-LAYER" "S" "Textos" "")
(command "-COLOR" "7")
(command "-TEXT" "S" "Standard" "J" "C" (list 1270 2335) 10 0 "20xTV")
(command "-LAYER" "S" "APs" "")
(command "-COLOR" "3")
(command "_.PLINE" (list 1290.0 3320) (list 1310.0 3320) (list 1300 3345) (list 1290.0 3320) "")
(command "_.CIRCLE" (list 1300 3345) 10)
(command "_.CIRCLE" (list 1300 3345) 21.25)
(command "_.CIRCLE" (list 1300 3345) 30)
(command "-LAYER" "S" "Textos" "")
(command "-COLOR" "7")
(command "-TEXT" "S" "Standard" "J" "C" (list 1270 3335) 10 0 "6xAP")
(command "-LAYER" "S" "Telefonos" "")
(command "-COLOR" "4")
(command "_.PLINE" (list 1290.0 3400) (list 1310.0 3400) (list 1310.0 3430) (list 1290.0 3430) "C")
(command "_.CIRCLE" (list 1300 3437) 5)
(command "-LAYER" "S" "Textos" "")
(command "-COLOR" "7")
(command "-TEXT" "S" "Standard" "J" "C" (list 1270 3415) 10 0 "3xTEL")
(command "-LAYER" "S" "TVs" "")
(command "-COLOR" "5")
(command "_.PLINE" (list 1280.0 3480) (list 1320.0 3480) (list 1320.0 3505) (list 1280.0 3505) "C")
(command "_.PLINE" (list 1290.0 3480) (list 1310.0 3480) (list 1300 3470) (list 1290.0 3480) "")
(command "-LAYER" "S" "Textos" "")
(command "-COLOR" "7")
(command "-TEXT" "S" "Standard" "J" "C" (list 1270 3495) 10 0 "11xTV")
(command "-LAYER" "S" "APs" "")
(command "-COLOR" "3")
(command "_.PLINE" (list 1290.0 4400) (list 1310.0 4400) (list 1300 4425) (list 1290.0 4400) "")
(command "_.CIRCLE" (list 1300 4425) 10)
(command "_.CIRCLE" (list 1300 4425) 21.25)
(command "_.CIRCLE" (list 1300 4425) 30)
(command "-LAYER" "S" "Textos" "")
(command "-COLOR" "7")
(command "-TEXT" "S" "Standard" "J" "C" (list 1270 4415) 10 0 "6xAP")
(command "-LAYER" "S" "Telefonos" "")
(command "-COLOR" "4")
(command "_.PLINE" (list 1290.0 4480) (list 1310.0 4480) (list 1310.0 4510) (list 1290.0 4510) "C")
(command "_.CIRCLE" (list 1300 4517) 5)
(command "-LAYER" "S" "Textos" "")
(command "-COLOR" "7")
(command "-TEXT" "S" "Standard" "J" "C" (list 1270 4495) 10 0 "3xTEL")
(command "-LAYER" "S" "TVs" "")
(command "-COLOR" "5")
(command "_.PLINE" (list 1280.0 4560) (list 1320.0 4560) (list 1320.0 4585) (list 1280.0 4585) "C")
(command "_.PLINE" (list 1290.0 4560) (list 1310.0 4560) (list 1300 4550) (list 1290.0 4560) "")
(command "-LAYER" "S" "Textos" "")
(command "-COLOR" "7")
(command "-TEXT" "S" "Standard" "J" "C" (list 1270 4575) 10 0 "10xTV")
(command "-LAYER" "S" "APs" "")
(command "-COLOR" "3")
(command "_.PLINE" (list 1290.0 5400) (list 1310.0 5400) (list 1300 5425) (list 1290.0 5400) "")
(command "_.CIRCLE" (list 1300 5425) 10)
(command "_.CIRCLE" (list 1300 5425) 21.25)
(command "_.CIRCLE" (list 1300 5425) 30)
(command "-LAYER" "S" "Textos" "")
(command "-COLOR" "7")
(command "-TEXT" "S" "Standard" "J" "C" (list 1270 5415) 10 0 "8xAP")
(command "-LAYER" "S" "Telefonos" "")
(command "-COLOR" "4")
(command "_.PLINE" (list 1290.0 5480) (list 1310.0 5480) (list 1310.0 5510) (list 1290.0 5510) "C")
(command "_.CIRCLE" (list 1300 5517) 5)
(command "-LAYER" "S" "Textos" "")
(command "-COLOR" "7")
(command "-TEXT" "S" "Standard" "J" "C" (list 1270 5495) 10 0 "4xTEL")
(command "-LAYER" "S" "TVs" "")
(command "-COLOR" "5")
(command "_.PLINE" (list 1280.0 5560) (list 1320.0 5560) (list 1320.0 5585) (list 1280.0 5585) "C")
(command "_.PLINE" (list 1290.0 5560) (list 1310.0 5560) (list 1300 5550) (list 1290.0 5560) "")
(command "-LAYER" "S" "Textos" "")
(command "-COLOR" "7")
(command "-TEXT" "S" "Standard" "J" "C" (list 1270 5575) 10 0 "13xTV")
(command "-LAYER" "S" "APs" "")
(command "-COLOR" "3")
(command "_.PLINE" (list 1290.0 6560) (list 1310.0 6560) (list 1300 6585) (list 1290.0 6560) "")
(command "_.CIRCLE" (list 1300 6585) 10)
(command "_.CIRCLE" (list 1300 6585) 21.25)
(command "_.CIRCLE" (list 1300 6585) 30)
(command "-LAYER" "S" "Textos" "")
(command "-COLOR" "7")
(command "-TEXT" "S" "Standard" "J" "C" (list 1270 6575) 10 0 "2xAP")
(command "-LAYER" "S" "Telefonos" "")
(command "-COLOR" "4")
(command "_.PLINE" (list 1290.0 6640) (list 1310.0 6640) (list 1310.0 6670) (list 1290.0 6670) "C")
(command "_.CIRCLE" (list 1300 6677) 5)
(command "-LAYER" "S" "Textos" "")
(command "-COLOR" "7")
(command "-TEXT" "S" "Standard" "J" "C" (list 1270 6655) 10 0 "1xTEL")
(command "-LAYER" "S" "TVs" "")
(command "-COLOR" "5")
(command "_.PLINE" (list 1280.0 6720) (list 1320.0 6720) (list 1320.0 6745) (list 1280.0 6745) "C")
(command "_.PLINE" (list 1290.0 6720) (list 1310.0 6720) (list 1300 6710) (list 1290.0 6720) "")
(command "-LAYER" "S" "Textos" "")
(command "-COLOR" "7")
(command "-TEXT" "S" "Standard" "J" "C" (list 1270 6735) 10 0 "4xTV")
(command "-LAYER" "S" "APs" "")
(command "-COLOR" "3")
(command "_.PLINE" (list 1290.0 7800) (list 1310.0 7800) (list 1300 7825) (list 1290.0 7800) "")
(command "_.CIRCLE" (list 1300 7825) 10)
(command "_.CIRCLE" (list 1300 7825) 21.25)
(command "_.CIRCLE" (list 1300 7825) 30)
(command "-LAYER" "S" "Textos" "")
(command "-COLOR" "7")
(command "-TEXT" "S" "Standard" "J" "C" (list 1270 7815) 10 0 "4xAP")
(command "-LAYER" "S" "Telefonos" "")
(command "-COLOR" "4")
(command "_.PLINE" (list 1290.0 7880) (list 1310.0 7880) (list 1310.0 7910) (list 1290.0 7910) "C")
(command "_.CIRCLE" (list 1300 7917) 5)
(command "-LAYER" "S" "Textos" "")
(command "-COLOR" "7")
(command "-TEXT" "S" "Standard" "J" "C" (list 1270 7895) 10 0 "2xTEL")
(command "-LAYER" "S" "TVs" "")
(command "-COLOR" "5")
(command "_.PLINE" (list 1280.0 7960) (list 1320.0 7960) (list 1320.0 7985) (list 1280.0 7985) "C")
(command "_.PLINE" (list 1290.0 7960) (list 1310.0 7960) (list 1300 7950) (list 1290.0 7960) "")
(command "-LAYER" "S" "Textos" "")
(command "-COLOR" "7")
(command "-TEXT" "S" "Standard" "J" "C" (list 1270 7975) 10 0 "7xTV")

; === DIBUJAR TORRE: IDF2 ===
(command "-LAYER" "S" "Textos" "")
(command "-COLOR" "7")
(command "-TEXT" "S" "Standard" "J" "C" (list 2200 150) 25 0 "IDF2")
(command "-LAYER" "S" "Switches" "")
(command "-COLOR" "6")
(command "_.PLINE" (list 2250 150) (list 2400 150) (list 2400 190) (list 2250 190) "C")
(command "-LAYER" "S" "Textos" "")
(command "-COLOR" "7")
(command "-TEXT" "S" "Standard" "J" "MC" (list 2325.0 170.0) 8 0 "SW-CCTV (DS-3E3728F)")
(command "-LAYER" "S" "Switches" "")
(command "-COLOR" "6")
(command "_.PLINE" (list 2250 250) (list 2400 250) (list 2400 290) (list 2250 290) "C")
(command "-LAYER" "S" "Textos" "")
(command "-COLOR" "7")
(command "-TEXT" "S" "Standard" "J" "MC" (list 2325.0 270.0) 8 0 "SW-DATA (Meraki MS225)")
(command "-LAYER" "S" "Switches" "")
(command "-COLOR" "6")
(command "_.PLINE" (list 2250 350) (list 2400 350) (list 2400 390) (list 2250 390) "C")
(command "-LAYER" "S" "Textos" "")
(command "-COLOR" "7")
(command "-TEXT" "S" "Standard" "J" "MC" (list 2325.0 370.0) 8 0 "SW-IPTV (RG-NBS6002)")
(command "-LAYER" "S" "Switches" "")
(command "-COLOR" "6")
(command "_.PLINE" (list 2250 450) (list 2400 450) (list 2400 490) (list 2250 490) "C")
(command "-LAYER" "S" "Textos" "")
(command "-COLOR" "7")
(command "-TEXT" "S" "Standard" "J" "MC" (list 2325.0 470.0) 8 0 "SW-TEL (Meraki MS225)")
(command "-LAYER" "S" "Switches" "")
(command "-COLOR" "6")
(command "_.PLINE" (list 2250 550) (list 2400 550) (list 2400 590) (list 2250 590) "C")
(command "-LAYER" "S" "Textos" "")
(command "-COLOR" "7")
(command "-TEXT" "S" "Standard" "J" "MC" (list 2325.0 570.0) 8 0 "SW-WIFI (Meraki MS225)")
(command "-LAYER" "S" "APs" "")
(command "-COLOR" "3")
(command "_.PLINE" (list 2340.0 3320) (list 2360.0 3320) (list 2350 3345) (list 2340.0 3320) "")
(command "_.CIRCLE" (list 2350 3345) 10)
(command "_.CIRCLE" (list 2350 3345) 21.25)
(command "_.CIRCLE" (list 2350 3345) 30)
(command "-LAYER" "S" "Textos" "")
(command "-COLOR" "7")
(command "-TEXT" "S" "Standard" "J" "C" (list 2320 3335) 10 0 "2xAP")
(command "-LAYER" "S" "Telefonos" "")
(command "-COLOR" "4")
(command "_.PLINE" (list 2340.0 3400) (list 2360.0 3400) (list 2360.0 3430) (list 2340.0 3430) "C")
(command "_.CIRCLE" (list 2350 3437) 5)
(command "-LAYER" "S" "Textos" "")
(command "-COLOR" "7")
(command "-TEXT" "S" "Standard" "J" "C" (list 2320 3415) 10 0 "1xTEL")
(command "-LAYER" "S" "TVs" "")
(command "-COLOR" "5")
(command "_.PLINE" (list 2330.0 3480) (list 2370.0 3480) (list 2370.0 3505) (list 2330.0 3505) "C")
(command "_.PLINE" (list 2340.0 3480) (list 2360.0 3480) (list 2350 3470) (list 2340.0 3480) "")
(command "-LAYER" "S" "Textos" "")
(command "-COLOR" "7")
(command "-TEXT" "S" "Standard" "J" "C" (list 2320 3495) 10 0 "3xTV")
(command "-LAYER" "S" "APs" "")
(command "-COLOR" "3")
(command "_.PLINE" (list 2340.0 4400) (list 2360.0 4400) (list 2350 4425) (list 2340.0 4400) "")
(command "_.CIRCLE" (list 2350 4425) 10)
(command "_.CIRCLE" (list 2350 4425) 21.25)
(command "_.CIRCLE" (list 2350 4425) 30)
(command "-LAYER" "S" "Textos" "")
(command "-COLOR" "7")
(command "-TEXT" "S" "Standard" "J" "C" (list 2320 4415) 10 0 "4xAP")
(command "-LAYER" "S" "Telefonos" "")
(command "-COLOR" "4")
(command "_.PLINE" (list 2340.0 4480) (list 2360.0 4480) (list 2360.0 4510) (list 2340.0 4510) "C")
(command "_.CIRCLE" (list 2350 4517) 5)
(command "-LAYER" "S" "Textos" "")
(command "-COLOR" "7")
(command "-TEXT" "S" "Standard" "J" "C" (list 2320 4495) 10 0 "2xTEL")
(command "-LAYER" "S" "TVs" "")
(command "-COLOR" "5")
(command "_.PLINE" (list 2330.0 4560) (list 2370.0 4560) (list 2370.0 4585) (list 2330.0 4585) "C")
(command "_.PLINE" (list 2340.0 4560) (list 2360.0 4560) (list 2350 4550) (list 2340.0 4560) "")
(command "-LAYER" "S" "Textos" "")
(command "-COLOR" "7")
(command "-TEXT" "S" "Standard" "J" "C" (list 2320 4575) 10 0 "7xTV")
(command "-LAYER" "S" "APs" "")
(command "-COLOR" "3")
(command "_.PLINE" (list 2340.0 5400) (list 2360.0 5400) (list 2350 5425) (list 2340.0 5400) "")
(command "_.CIRCLE" (list 2350 5425) 10)
(command "_.CIRCLE" (list 2350 5425) 21.25)
(command "_.CIRCLE" (list 2350 5425) 30)
(command "-LAYER" "S" "Textos" "")
(command "-COLOR" "7")
(command "-TEXT" "S" "Standard" "J" "C" (list 2320 5415) 10 0 "6xAP")
(command "-LAYER" "S" "Telefonos" "")
(command "-COLOR" "4")
(command "_.PLINE" (list 2340.0 5480) (list 2360.0 5480) (list 2360.0 5510) (list 2340.0 5510) "C")
(command "_.CIRCLE" (list 2350 5517) 5)
(command "-LAYER" "S" "Textos" "")
(command "-COLOR" "7")
(command "-TEXT" "S" "Standard" "J" "C" (list 2320 5495) 10 0 "3xTEL")
(command "-LAYER" "S" "TVs" "")
(command "-COLOR" "5")
(command "_.PLINE" (list 2330.0 5560) (list 2370.0 5560) (list 2370.0 5585) (list 2330.0 5585) "C")
(command "_.PLINE" (list 2340.0 5560) (list 2360.0 5560) (list 2350 5550) (list 2340.0 5560) "")
(command "-LAYER" "S" "Textos" "")
(command "-COLOR" "7")
(command "-TEXT" "S" "Standard" "J" "C" (list 2320 5575) 10 0 "10xTV")
(command "-LAYER" "S" "APs" "")
(command "-COLOR" "3")
(command "_.PLINE" (list 2340.0 6560) (list 2360.0 6560) (list 2350 6585) (list 2340.0 6560) "")
(command "_.CIRCLE" (list 2350 6585) 10)
(command "_.CIRCLE" (list 2350 6585) 21.25)
(command "_.CIRCLE" (list 2350 6585) 30)
(command "-LAYER" "S" "Textos" "")
(command "-COLOR" "7")
(command "-TEXT" "S" "Standard" "J" "C" (list 2320 6575) 10 0 "4xAP")
(command "-LAYER" "S" "Telefonos" "")
(command "-COLOR" "4")
(command "_.PLINE" (list 2340.0 6640) (list 2360.0 6640) (list 2360.0 6670) (list 2340.0 6670) "C")
(command "_.CIRCLE" (list 2350 6677) 5)
(command "-LAYER" "S" "Textos" "")
(command "-COLOR" "7")
(command "-TEXT" "S" "Standard" "J" "C" (list 2320 6655) 10 0 "2xTEL")
(command "-LAYER" "S" "TVs" "")
(command "-COLOR" "5")
(command "_.PLINE" (list 2330.0 6720) (list 2370.0 6720) (list 2370.0 6745) (list 2330.0 6745) "C")
(command "_.PLINE" (list 2340.0 6720) (list 2360.0 6720) (list 2350 6710) (list 2340.0 6720) "")
(command "-LAYER" "S" "Textos" "")
(command "-COLOR" "7")
(command "-TEXT" "S" "Standard" "J" "C" (list 2320 6735) 10 0 "7xTV")
(command "-LAYER" "S" "APs" "")
(command "-COLOR" "3")
(command "_.PLINE" (list 2340.0 7800) (list 2360.0 7800) (list 2350 7825) (list 2340.0 7800) "")
(command "_.CIRCLE" (list 2350 7825) 10)
(command "_.CIRCLE" (list 2350 7825) 21.25)
(command "_.CIRCLE" (list 2350 7825) 30)
(command "-LAYER" "S" "Textos" "")
(command "-COLOR" "7")
(command "-TEXT" "S" "Standard" "J" "C" (list 2320 7815) 10 0 "2xAP")
(command "-LAYER" "S" "Telefonos" "")
(command "-COLOR" "4")
(command "_.PLINE" (list 2340.0 7880) (list 2360.0 7880) (list 2360.0 7910) (list 2340.0 7910) "C")
(command "_.CIRCLE" (list 2350 7917) 5)
(command "-LAYER" "S" "Textos" "")
(command "-COLOR" "7")
(command "-TEXT" "S" "Standard" "J" "C" (list 2320 7895) 10 0 "1xTEL")
(command "-LAYER" "S" "TVs" "")
(command "-COLOR" "5")
(command "_.PLINE" (list 2330.0 7960) (list 2370.0 7960) (list 2370.0 7985) (list 2330.0 7985) "C")
(command "_.PLINE" (list 2340.0 7960) (list 2360.0 7960) (list 2350 7950) (list 2340.0 7960) "")
(command "-LAYER" "S" "Textos" "")
(command "-COLOR" "7")
(command "-TEXT" "S" "Standard" "J" "C" (list 2320 7975) 10 0 "3xTV")

; === DIBUJAR TORRE: IDF3 ===
(command "-LAYER" "S" "Textos" "")
(command "-COLOR" "7")
(command "-TEXT" "S" "Standard" "J" "C" (list 3250 150) 25 0 "IDF3")
(command "-LAYER" "S" "Switches" "")
(command "-COLOR" "6")
(command "_.PLINE" (list 3300 150) (list 3450 150) (list 3450 190) (list 3300 190) "C")
(command "-LAYER" "S" "Textos" "")
(command "-COLOR" "7")
(command "-TEXT" "S" "Standard" "J" "MC" (list 3375.0 170.0) 8 0 "SW-CCTV (DS-3E3728F)")
(command "-LAYER" "S" "Switches" "")
(command "-COLOR" "6")
(command "_.PLINE" (list 3300 250) (list 3450 250) (list 3450 290) (list 3300 290) "C")
(command "-LAYER" "S" "Textos" "")
(command "-COLOR" "7")
(command "-TEXT" "S" "Standard" "J" "MC" (list 3375.0 270.0) 8 0 "SW-DATA (Meraki MS225)")
(command "-LAYER" "S" "Switches" "")
(command "-COLOR" "6")
(command "_.PLINE" (list 3300 350) (list 3450 350) (list 3450 390) (list 3300 390) "C")
(command "-LAYER" "S" "Textos" "")
(command "-COLOR" "7")
(command "-TEXT" "S" "Standard" "J" "MC" (list 3375.0 370.0) 8 0 "SW-IPTV (RG-NBS6002)")
(command "-LAYER" "S" "Switches" "")
(command "-COLOR" "6")
(command "_.PLINE" (list 3300 450) (list 3450 450) (list 3450 490) (list 3300 490) "C")
(command "-LAYER" "S" "Textos" "")
(command "-COLOR" "7")
(command "-TEXT" "S" "Standard" "J" "MC" (list 3375.0 470.0) 8 0 "SW-TEL (Meraki MS225)")
(command "-LAYER" "S" "Switches" "")
(command "-COLOR" "6")
(command "_.PLINE" (list 3300 550) (list 3450 550) (list 3450 590) (list 3300 590) "C")
(command "-LAYER" "S" "Textos" "")
(command "-COLOR" "7")
(command "-TEXT" "S" "Standard" "J" "MC" (list 3375.0 570.0) 8 0 "SW-WIFI (Meraki MS225)")
(command "-LAYER" "S" "APs" "")
(command "-COLOR" "3")
(command "_.PLINE" (list 3390.0 840) (list 3410.0 840) (list 3400 865) (list 3390.0 840) "")
(command "_.CIRCLE" (list 3400 865) 10)
(command "_.CIRCLE" (list 3400 865) 21.25)
(command "_.CIRCLE" (list 3400 865) 30)
(command "-LAYER" "S" "Textos" "")
(command "-COLOR" "7")
(command "-TEXT" "S" "Standard" "J" "C" (list 3370 855) 10 0 "8xAP")
(command "-LAYER" "S" "Telefonos" "")
(command "-COLOR" "4")
(command "_.PLINE" (list 3390.0 920) (list 3410.0 920) (list 3410.0 950) (list 3390.0 950) "C")
(command "_.CIRCLE" (list 3400 957) 5)
(command "-LAYER" "S" "Textos" "")
(command "-COLOR" "7")
(command "-TEXT" "S" "Standard" "J" "C" (list 3370 935) 10 0 "4xTEL")
(command "-LAYER" "S" "TVs" "")
(command "-COLOR" "5")
(command "_.PLINE" (list 3380.0 1000) (list 3420.0 1000) (list 3420.0 1025) (list 3380.0 1025) "C")
(command "_.PLINE" (list 3390.0 1000) (list 3410.0 1000) (list 3400 990) (list 3390.0 1000) "")
(command "-LAYER" "S" "Textos" "")
(command "-COLOR" "7")
(command "-TEXT" "S" "Standard" "J" "C" (list 3370 1015) 10 0 "15xTV")
(command "-LAYER" "S" "APs" "")
(command "-COLOR" "3")
(command "_.PLINE" (list 3390.0 2160) (list 3410.0 2160) (list 3400 2185) (list 3390.0 2160) "")
(command "_.CIRCLE" (list 3400 2185) 10)
(command "_.CIRCLE" (list 3400 2185) 21.25)
(command "_.CIRCLE" (list 3400 2185) 30)
(command "-LAYER" "S" "Textos" "")
(command "-COLOR" "7")
(command "-TEXT" "S" "Standard" "J" "C" (list 3370 2175) 10 0 "2xAP")
(command "-LAYER" "S" "Telefonos" "")
(command "-COLOR" "4")
(command "_.PLINE" (list 3390.0 2240) (list 3410.0 2240) (list 3410.0 2270) (list 3390.0 2270) "C")
(command "_.CIRCLE" (list 3400 2277) 5)
(command "-LAYER" "S" "Textos" "")
(command "-COLOR" "7")
(command "-TEXT" "S" "Standard" "J" "C" (list 3370 2255) 10 0 "1xTEL")
(command "-LAYER" "S" "TVs" "")
(command "-COLOR" "5")
(command "_.PLINE" (list 3380.0 2320) (list 3420.0 2320) (list 3420.0 2345) (list 3380.0 2345) "C")
(command "_.PLINE" (list 3390.0 2320) (list 3410.0 2320) (list 3400 2310) (list 3390.0 2320) "")
(command "-LAYER" "S" "Textos" "")
(command "-COLOR" "7")
(command "-TEXT" "S" "Standard" "J" "C" (list 3370 2335) 10 0 "4xTV")
(command "-LAYER" "S" "APs" "")
(command "-COLOR" "3")
(command "_.PLINE" (list 3390.0 3320) (list 3410.0 3320) (list 3400 3345) (list 3390.0 3320) "")
(command "_.CIRCLE" (list 3400 3345) 10)
(command "_.CIRCLE" (list 3400 3345) 21.25)
(command "_.CIRCLE" (list 3400 3345) 30)
(command "-LAYER" "S" "Textos" "")
(command "-COLOR" "7")
(command "-TEXT" "S" "Standard" "J" "C" (list 3370 3335) 10 0 "2xAP")
(command "-LAYER" "S" "Telefonos" "")
(command "-COLOR" "4")
(command "_.PLINE" (list 3390.0 3400) (list 3410.0 3400) (list 3410.0 3430) (list 3390.0 3430) "C")
(command "_.CIRCLE" (list 3400 3437) 5)
(command "-LAYER" "S" "Textos" "")
(command "-COLOR" "7")
(command "-TEXT" "S" "Standard" "J" "C" (list 3370 3415) 10 0 "1xTEL")
(command "-LAYER" "S" "TVs" "")
(command "-COLOR" "5")
(command "_.PLINE" (list 3380.0 3480) (list 3420.0 3480) (list 3420.0 3505) (list 3380.0 3505) "C")
(command "_.PLINE" (list 3390.0 3480) (list 3410.0 3480) (list 3400 3470) (list 3390.0 3480) "")
(command "-LAYER" "S" "Textos" "")
(command "-COLOR" "7")
(command "-TEXT" "S" "Standard" "J" "C" (list 3370 3495) 10 0 "3xTV")
(command "-LAYER" "S" "APs" "")
(command "-COLOR" "3")
(command "_.PLINE" (list 3390.0 4400) (list 3410.0 4400) (list 3400 4425) (list 3390.0 4400) "")
(command "_.CIRCLE" (list 3400 4425) 10)
(command "_.CIRCLE" (list 3400 4425) 21.25)
(command "_.CIRCLE" (list 3400 4425) 30)
(command "-LAYER" "S" "Textos" "")
(command "-COLOR" "7")
(command "-TEXT" "S" "Standard" "J" "C" (list 3370 4415) 10 0 "3xAP")
(command "-LAYER" "S" "Telefonos" "")
(command "-COLOR" "4")
(command "_.PLINE" (list 3390.0 4480) (list 3410.0 4480) (list 3410.0 4510) (list 3390.0 4510) "C")
(command "_.CIRCLE" (list 3400 4517) 5)
(command "-LAYER" "S" "Textos" "")
(command "-COLOR" "7")
(command "-TEXT" "S" "Standard" "J" "C" (list 3370 4495) 10 0 "1xTEL")
(command "-LAYER" "S" "TVs" "")
(command "-COLOR" "5")
(command "_.PLINE" (list 3380.0 4560) (list 3420.0 4560) (list 3420.0 4585) (list 3380.0 4585) "C")
(command "_.PLINE" (list 3390.0 4560) (list 3410.0 4560) (list 3400 4550) (list 3390.0 4560) "")
(command "-LAYER" "S" "Textos" "")
(command "-COLOR" "7")
(command "-TEXT" "S" "Standard" "J" "C" (list 3370 4575) 10 0 "5xTV")
(command "-LAYER" "S" "APs" "")
(command "-COLOR" "3")
(command "_.PLINE" (list 3390.0 5400) (list 3410.0 5400) (list 3400 5425) (list 3390.0 5400) "")
(command "_.CIRCLE" (list 3400 5425) 10)
(command "_.CIRCLE" (list 3400 5425) 21.25)
(command "_.CIRCLE" (list 3400 5425) 30)
(command "-LAYER" "S" "Textos" "")
(command "-COLOR" "7")
(command "-TEXT" "S" "Standard" "J" "C" (list 3370 5415) 10 0 "2xAP")
(command "-LAYER" "S" "Telefonos" "")
(command "-COLOR" "4")
(command "_.PLINE" (list 3390.0 5480) (list 3410.0 5480) (list 3410.0 5510) (list 3390.0 5510) "C")
(command "_.CIRCLE" (list 3400 5517) 5)
(command "-LAYER" "S" "Textos" "")
(command "-COLOR" "7")
(command "-TEXT" "S" "Standard" "J" "C" (list 3370 5495) 10 0 "1xTEL")
(command "-LAYER" "S" "TVs" "")
(command "-COLOR" "5")
(command "_.PLINE" (list 3380.0 5560) (list 3420.0 5560) (list 3420.0 5585) (list 3380.0 5585) "C")
(command "_.PLINE" (list 3390.0 5560) (list 3410.0 5560) (list 3400 5550) (list 3390.0 5560) "")
(command "-LAYER" "S" "Textos" "")
(command "-COLOR" "7")
(command "-TEXT" "S" "Standard" "J" "C" (list 3370 5575) 10 0 "3xTV")
(command "-LAYER" "S" "APs" "")
(command "-COLOR" "3")
(command "_.PLINE" (list 3390.0 6560) (list 3410.0 6560) (list 3400 6585) (list 3390.0 6560) "")
(command "_.CIRCLE" (list 3400 6585) 10)
(command "_.CIRCLE" (list 3400 6585) 21.25)
(command "_.CIRCLE" (list 3400 6585) 30)
(command "-LAYER" "S" "Textos" "")
(command "-COLOR" "7")
(command "-TEXT" "S" "Standard" "J" "C" (list 3370 6575) 10 0 "2xAP")
(command "-LAYER" "S" "Telefonos" "")
(command "-COLOR" "4")
(command "_.PLINE" (list 3390.0 6640) (list 3410.0 6640) (list 3410.0 6670) (list 3390.0 6670) "C")
(command "_.CIRCLE" (list 3400 6677) 5)
(command "-LAYER" "S" "Textos" "")
(command "-COLOR" "7")
(command "-TEXT" "S" "Standard" "J" "C" (list 3370 6655) 10 0 "1xTEL")
(command "-LAYER" "S" "TVs" "")
(command "-COLOR" "5")
(command "_.PLINE" (list 3380.0 6720) (list 3420.0 6720) (list 3420.0 6745) (list 3380.0 6745) "C")
(command "_.PLINE" (list 3390.0 6720) (list 3410.0 6720) (list 3400 6710) (list 3390.0 6720) "")
(command "-LAYER" "S" "Textos" "")
(command "-COLOR" "7")
(command "-TEXT" "S" "Standard" "J" "C" (list 3370 6735) 10 0 "4xTV")
(command "-LAYER" "S" "APs" "")
(command "-COLOR" "3")
(command "_.PLINE" (list 3390.0 7800) (list 3410.0 7800) (list 3400 7825) (list 3390.0 7800) "")
(command "_.CIRCLE" (list 3400 7825) 10)
(command "_.CIRCLE" (list 3400 7825) 21.25)
(command "_.CIRCLE" (list 3400 7825) 30)
(command "-LAYER" "S" "Textos" "")
(command "-COLOR" "7")
(command "-TEXT" "S" "Standard" "J" "C" (list 3370 7815) 10 0 "10xAP")
(command "-LAYER" "S" "Telefonos" "")
(command "-COLOR" "4")
(command "_.PLINE" (list 3390.0 7880) (list 3410.0 7880) (list 3410.0 7910) (list 3390.0 7910) "C")
(command "_.CIRCLE" (list 3400 7917) 5)
(command "-LAYER" "S" "Textos" "")
(command "-COLOR" "7")
(command "-TEXT" "S" "Standard" "J" "C" (list 3370 7895) 10 0 "5xTEL")
(command "-LAYER" "S" "TVs" "")
(command "-COLOR" "5")
(command "_.PLINE" (list 3380.0 7960) (list 3420.0 7960) (list 3420.0 7985) (list 3380.0 7985) "C")
(command "_.PLINE" (list 3390.0 7960) (list 3410.0 7960) (list 3400 7950) (list 3390.0 7960) "")
(command "-LAYER" "S" "Textos" "")
(command "-COLOR" "7")
(command "-TEXT" "S" "Standard" "J" "C" (list 3370 7975) 10 0 "17xTV")

; === DIBUJAR TORRE: IDF4 ===
(command "-LAYER" "S" "Textos" "")
(command "-COLOR" "7")
(command "-TEXT" "S" "Standard" "J" "C" (list 4300 150) 25 0 "IDF4")
(command "-LAYER" "S" "Switches" "")
(command "-COLOR" "6")
(command "_.PLINE" (list 4350 150) (list 4500 150) (list 4500 190) (list 4350 190) "C")
(command "-LAYER" "S" "Textos" "")
(command "-COLOR" "7")
(command "-TEXT" "S" "Standard" "J" "MC" (list 4425.0 170.0) 8 0 "SW-CCTV (DS-3E3728F)")
(command "-LAYER" "S" "Switches" "")
(command "-COLOR" "6")
(command "_.PLINE" (list 4350 250) (list 4500 250) (list 4500 290) (list 4350 290) "C")
(command "-LAYER" "S" "Textos" "")
(command "-COLOR" "7")
(command "-TEXT" "S" "Standard" "J" "MC" (list 4425.0 270.0) 8 0 "SW-DATA (Meraki MS225)")
(command "-LAYER" "S" "Switches" "")
(command "-COLOR" "6")
(command "_.PLINE" (list 4350 350) (list 4500 350) (list 4500 390) (list 4350 390) "C")
(command "-LAYER" "S" "Textos" "")
(command "-COLOR" "7")
(command "-TEXT" "S" "Standard" "J" "MC" (list 4425.0 370.0) 8 0 "SW-IPTV (RG-NBS6002)")
(command "-LAYER" "S" "Switches" "")
(command "-COLOR" "6")
(command "_.PLINE" (list 4350 450) (list 4500 450) (list 4500 490) (list 4350 490) "C")
(command "-LAYER" "S" "Textos" "")
(command "-COLOR" "7")
(command "-TEXT" "S" "Standard" "J" "MC" (list 4425.0 470.0) 8 0 "SW-TEL (Meraki MS225)")
(command "-LAYER" "S" "Switches" "")
(command "-COLOR" "6")
(command "_.PLINE" (list 4350 550) (list 4500 550) (list 4500 590) (list 4350 590) "C")
(command "-LAYER" "S" "Textos" "")
(command "-COLOR" "7")
(command "-TEXT" "S" "Standard" "J" "MC" (list 4425.0 570.0) 8 0 "SW-WIFI (Meraki MS225)")
(command "-LAYER" "S" "APs" "")
(command "-COLOR" "3")
(command "_.PLINE" (list 4440.0 840) (list 4460.0 840) (list 4450 865) (list 4440.0 840) "")
(command "_.CIRCLE" (list 4450 865) 10)
(command "_.CIRCLE" (list 4450 865) 21.25)
(command "_.CIRCLE" (list 4450 865) 30)
(command "-LAYER" "S" "Textos" "")
(command "-COLOR" "7")
(command "-TEXT" "S" "Standard" "J" "C" (list 4420 855) 10 0 "6xAP")
(command "-LAYER" "S" "Telefonos" "")
(command "-COLOR" "4")
(command "_.PLINE" (list 4440.0 920) (list 4460.0 920) (list 4460.0 950) (list 4440.0 950) "C")
(command "_.CIRCLE" (list 4450 957) 5)
(command "-LAYER" "S" "Textos" "")
(command "-COLOR" "7")
(command "-TEXT" "S" "Standard" "J" "C" (list 4420 935) 10 0 "3xTEL")
(command "-LAYER" "S" "TVs" "")
(command "-COLOR" "5")
(command "_.PLINE" (list 4430.0 1000) (list 4470.0 1000) (list 4470.0 1025) (list 4430.0 1025) "C")
(command "_.PLINE" (list 4440.0 1000) (list 4460.0 1000) (list 4450 990) (list 4440.0 1000) "")
(command "-LAYER" "S" "Textos" "")
(command "-COLOR" "7")
(command "-TEXT" "S" "Standard" "J" "C" (list 4420 1015) 10 0 "10xTV")
(command "-LAYER" "S" "APs" "")
(command "-COLOR" "3")
(command "_.PLINE" (list 4440.0 2160) (list 4460.0 2160) (list 4450 2185) (list 4440.0 2160) "")
(command "_.CIRCLE" (list 4450 2185) 10)
(command "_.CIRCLE" (list 4450 2185) 21.25)
(command "_.CIRCLE" (list 4450 2185) 30)
(command "-LAYER" "S" "Textos" "")
(command "-COLOR" "7")
(command "-TEXT" "S" "Standard" "J" "C" (list 4420 2175) 10 0 "7xAP")
(command "-LAYER" "S" "Telefonos" "")
(command "-COLOR" "4")
(command "_.PLINE" (list 4440.0 2240) (list 4460.0 2240) (list 4460.0 2270) (list 4440.0 2270) "C")
(command "_.CIRCLE" (list 4450 2277) 5)
(command "-LAYER" "S" "Textos" "")
(command "-COLOR" "7")
(command "-TEXT" "S" "Standard" "J" "C" (list 4420 2255) 10 0 "3xTEL")
(command "-LAYER" "S" "TVs" "")
(command "-COLOR" "5")
(command "_.PLINE" (list 4430.0 2320) (list 4470.0 2320) (list 4470.0 2345) (list 4430.0 2345) "C")
(command "_.PLINE" (list 4440.0 2320) (list 4460.0 2320) (list 4450 2310) (list 4440.0 2320) "")
(command "-LAYER" "S" "Textos" "")
(command "-COLOR" "7")
(command "-TEXT" "S" "Standard" "J" "C" (list 4420 2335) 10 0 "12xTV")
(command "-LAYER" "S" "APs" "")
(command "-COLOR" "3")
(command "_.PLINE" (list 4440.0 3320) (list 4460.0 3320) (list 4450 3345) (list 4440.0 3320) "")
(command "_.CIRCLE" (list 4450 3345) 10)
(command "_.CIRCLE" (list 4450 3345) 21.25)
(command "_.CIRCLE" (list 4450 3345) 30)
(command "-LAYER" "S" "Textos" "")
(command "-COLOR" "7")
(command "-TEXT" "S" "Standard" "J" "C" (list 4420 3335) 10 0 "7xAP")
(command "-LAYER" "S" "Telefonos" "")
(command "-COLOR" "4")
(command "_.PLINE" (list 4440.0 3400) (list 4460.0 3400) (list 4460.0 3430) (list 4440.0 3430) "C")
(command "_.CIRCLE" (list 4450 3437) 5)
(command "-LAYER" "S" "Textos" "")
(command "-COLOR" "7")
(command "-TEXT" "S" "Standard" "J" "C" (list 4420 3415) 10 0 "3xTEL")
(command "-LAYER" "S" "TVs" "")
(command "-COLOR" "5")
(command "_.PLINE" (list 4430.0 3480) (list 4470.0 3480) (list 4470.0 3505) (list 4430.0 3505) "C")
(command "_.PLINE" (list 4440.0 3480) (list 4460.0 3480) (list 4450 3470) (list 4440.0 3480) "")
(command "-LAYER" "S" "Textos" "")
(command "-COLOR" "7")
(command "-TEXT" "S" "Standard" "J" "C" (list 4420 3495) 10 0 "10xTV")
(command "-LAYER" "S" "APs" "")
(command "-COLOR" "3")
(command "_.PLINE" (list 4440.0 4400) (list 4460.0 4400) (list 4450 4425) (list 4440.0 4400) "")
(command "_.CIRCLE" (list 4450 4425) 10)
(command "_.CIRCLE" (list 4450 4425) 21.25)
(command "_.CIRCLE" (list 4450 4425) 30)
(command "-LAYER" "S" "Textos" "")
(command "-COLOR" "7")
(command "-TEXT" "S" "Standard" "J" "C" (list 4420 4415) 10 0 "6xAP")
(command "-LAYER" "S" "Telefonos" "")
(command "-COLOR" "4")
(command "_.PLINE" (list 4440.0 4480) (list 4460.0 4480) (list 4460.0 4510) (list 4440.0 4510) "C")
(command "_.CIRCLE" (list 4450 4517) 5)
(command "-LAYER" "S" "Textos" "")
(command "-COLOR" "7")
(command "-TEXT" "S" "Standard" "J" "C" (list 4420 4495) 10 0 "3xTEL")
(command "-LAYER" "S" "TVs" "")
(command "-COLOR" "5")
(command "_.PLINE" (list 4430.0 4560) (list 4470.0 4560) (list 4470.0 4585) (list 4430.0 4585) "C")
(command "_.PLINE" (list 4440.0 4560) (list 4460.0 4560) (list 4450 4550) (list 4440.0 4560) "")
(command "-LAYER" "S" "Textos" "")
(command "-COLOR" "7")
(command "-TEXT" "S" "Standard" "J" "C" (list 4420 4575) 10 0 "9xTV")
(command "-LAYER" "S" "APs" "")
(command "-COLOR" "3")
(command "_.PLINE" (list 4440.0 5400) (list 4460.0 5400) (list 4450 5425) (list 4440.0 5400) "")
(command "_.CIRCLE" (list 4450 5425) 10)
(command "_.CIRCLE" (list 4450 5425) 21.25)
(command "_.CIRCLE" (list 4450 5425) 30)
(command "-LAYER" "S" "Textos" "")
(command "-COLOR" "7")
(command "-TEXT" "S" "Standard" "J" "C" (list 4420 5415) 10 0 "6xAP")
(command "-LAYER" "S" "Telefonos" "")
(command "-COLOR" "4")
(command "_.PLINE" (list 4440.0 5480) (list 4460.0 5480) (list 4460.0 5510) (list 4440.0 5510) "C")
(command "_.CIRCLE" (list 4450 5517) 5)
(command "-LAYER" "S" "Textos" "")
(command "-COLOR" "7")
(command "-TEXT" "S" "Standard" "J" "C" (list 4420 5495) 10 0 "3xTEL")
(command "-LAYER" "S" "TVs" "")
(command "-COLOR" "5")
(command "_.PLINE" (list 4430.0 5560) (list 4470.0 5560) (list 4470.0 5585) (list 4430.0 5585) "C")
(command "_.PLINE" (list 4440.0 5560) (list 4460.0 5560) (list 4450 5550) (list 4440.0 5560) "")
(command "-LAYER" "S" "Textos" "")
(command "-COLOR" "7")
(command "-TEXT" "S" "Standard" "J" "C" (list 4420 5575) 10 0 "10xTV")
(command "-LAYER" "S" "APs" "")
(command "-COLOR" "3")
(command "_.PLINE" (list 4440.0 6560) (list 4460.0 6560) (list 4450 6585) (list 4440.0 6560) "")
(command "_.CIRCLE" (list 4450 6585) 10)
(command "_.CIRCLE" (list 4450 6585) 21.25)
(command "_.CIRCLE" (list 4450 6585) 30)
(command "-LAYER" "S" "Textos" "")
(command "-COLOR" "7")
(command "-TEXT" "S" "Standard" "J" "C" (list 4420 6575) 10 0 "6xAP")
(command "-LAYER" "S" "Telefonos" "")
(command "-COLOR" "4")
(command "_.PLINE" (list 4440.0 6640) (list 4460.0 6640) (list 4460.0 6670) (list 4440.0 6670) "C")
(command "_.CIRCLE" (list 4450 6677) 5)
(command "-LAYER" "S" "Textos" "")
(command "-COLOR" "7")
(command "-TEXT" "S" "Standard" "J" "C" (list 4420 6655) 10 0 "3xTEL")
(command "-LAYER" "S" "TVs" "")
(command "-COLOR" "5")
(command "_.PLINE" (list 4430.0 6720) (list 4470.0 6720) (list 4470.0 6745) (list 4430.0 6745) "C")
(command "_.PLINE" (list 4440.0 6720) (list 4460.0 6720) (list 4450 6710) (list 4440.0 6720) "")
(command "-LAYER" "S" "Textos" "")
(command "-COLOR" "7")
(command "-TEXT" "S" "Standard" "J" "C" (list 4420 6735) 10 0 "10xTV")
(command "-LAYER" "S" "APs" "")
(command "-COLOR" "3")
(command "_.PLINE" (list 4440.0 7800) (list 4460.0 7800) (list 4450 7825) (list 4440.0 7800) "")
(command "_.CIRCLE" (list 4450 7825) 10)
(command "_.CIRCLE" (list 4450 7825) 21.25)
(command "_.CIRCLE" (list 4450 7825) 30)
(command "-LAYER" "S" "Textos" "")
(command "-COLOR" "7")
(command "-TEXT" "S" "Standard" "J" "C" (list 4420 7815) 10 0 "2xAP")
(command "-LAYER" "S" "Telefonos" "")
(command "-COLOR" "4")
(command "_.PLINE" (list 4440.0 7880) (list 4460.0 7880) (list 4460.0 7910) (list 4440.0 7910) "C")
(command "_.CIRCLE" (list 4450 7917) 5)
(command "-LAYER" "S" "Textos" "")
(command "-COLOR" "7")
(command "-TEXT" "S" "Standard" "J" "C" (list 4420 7895) 10 0 "1xTEL")
(command "-LAYER" "S" "TVs" "")
(command "-COLOR" "5")
(command "_.PLINE" (list 4430.0 7960) (list 4470.0 7960) (list 4470.0 7985) (list 4430.0 7985) "C")
(command "_.PLINE" (list 4440.0 7960) (list 4460.0 7960) (list 4450 7950) (list 4440.0 7960) "")
(command "-LAYER" "S" "Textos" "")
(command "-COLOR" "7")
(command "-TEXT" "S" "Standard" "J" "C" (list 4420 7975) 10 0 "3xTV")

; === DIBUJAR TORRE: IDF5 ===
(command "-LAYER" "S" "Textos" "")
(command "-COLOR" "7")
(command "-TEXT" "S" "Standard" "J" "C" (list 5350 150) 25 0 "IDF5")
(command "-LAYER" "S" "Switches" "")
(command "-COLOR" "6")
(command "_.PLINE" (list 5400 150) (list 5550 150) (list 5550 190) (list 5400 190) "C")
(command "-LAYER" "S" "Textos" "")
(command "-COLOR" "7")
(command "-TEXT" "S" "Standard" "J" "MC" (list 5475.0 170.0) 8 0 "SW-CCTV (DS-3E3728F)")
(command "-LAYER" "S" "Switches" "")
(command "-COLOR" "6")
(command "_.PLINE" (list 5400 250) (list 5550 250) (list 5550 290) (list 5400 290) "C")
(command "-LAYER" "S" "Textos" "")
(command "-COLOR" "7")
(command "-TEXT" "S" "Standard" "J" "MC" (list 5475.0 270.0) 8 0 "SW-DATA (Meraki MS225)")
(command "-LAYER" "S" "Switches" "")
(command "-COLOR" "6")
(command "_.PLINE" (list 5400 350) (list 5550 350) (list 5550 390) (list 5400 390) "C")
(command "-LAYER" "S" "Textos" "")
(command "-COLOR" "7")
(command "-TEXT" "S" "Standard" "J" "MC" (list 5475.0 370.0) 8 0 "SW-IPTV (RG-NBS6002)")
(command "-LAYER" "S" "Switches" "")
(command "-COLOR" "6")
(command "_.PLINE" (list 5400 450) (list 5550 450) (list 5550 490) (list 5400 490) "C")
(command "-LAYER" "S" "Textos" "")
(command "-COLOR" "7")
(command "-TEXT" "S" "Standard" "J" "MC" (list 5475.0 470.0) 8 0 "SW-TEL (Meraki MS225)")
(command "-LAYER" "S" "Switches" "")
(command "-COLOR" "6")
(command "_.PLINE" (list 5400 550) (list 5550 550) (list 5550 590) (list 5400 590) "C")
(command "-LAYER" "S" "Textos" "")
(command "-COLOR" "7")
(command "-TEXT" "S" "Standard" "J" "MC" (list 5475.0 570.0) 8 0 "SW-WIFI (Meraki MS225)")
(command "-LAYER" "S" "APs" "")
(command "-COLOR" "3")
(command "_.PLINE" (list 5490.0 840) (list 5510.0 840) (list 5500 865) (list 5490.0 840) "")
(command "_.CIRCLE" (list 5500 865) 10)
(command "_.CIRCLE" (list 5500 865) 21.25)
(command "_.CIRCLE" (list 5500 865) 30)
(command "-LAYER" "S" "Textos" "")
(command "-COLOR" "7")
(command "-TEXT" "S" "Standard" "J" "C" (list 5470 855) 10 0 "2xAP")
(command "-LAYER" "S" "Telefonos" "")
(command "-COLOR" "4")
(command "_.PLINE" (list 5490.0 920) (list 5510.0 920) (list 5510.0 950) (list 5490.0 950) "C")
(command "_.CIRCLE" (list 5500 957) 5)
(command "-LAYER" "S" "Textos" "")
(command "-COLOR" "7")
(command "-TEXT" "S" "Standard" "J" "C" (list 5470 935) 10 0 "1xTEL")
(command "-LAYER" "S" "TVs" "")
(command "-COLOR" "5")
(command "_.PLINE" (list 5480.0 1000) (list 5520.0 1000) (list 5520.0 1025) (list 5480.0 1025) "C")
(command "_.PLINE" (list 5490.0 1000) (list 5510.0 1000) (list 5500 990) (list 5490.0 1000) "")
(command "-LAYER" "S" "Textos" "")
(command "-COLOR" "7")
(command "-TEXT" "S" "Standard" "J" "C" (list 5470 1015) 10 0 "4xTV")
(command "-LAYER" "S" "APs" "")
(command "-COLOR" "3")
(command "_.PLINE" (list 5490.0 2160) (list 5510.0 2160) (list 5500 2185) (list 5490.0 2160) "")
(command "_.CIRCLE" (list 5500 2185) 10)
(command "_.CIRCLE" (list 5500 2185) 21.25)
(command "_.CIRCLE" (list 5500 2185) 30)
(command "-LAYER" "S" "Textos" "")
(command "-COLOR" "7")
(command "-TEXT" "S" "Standard" "J" "C" (list 5470 2175) 10 0 "4xAP")
(command "-LAYER" "S" "Telefonos" "")
(command "-COLOR" "4")
(command "_.PLINE" (list 5490.0 2240) (list 5510.0 2240) (list 5510.0 2270) (list 5490.0 2270) "C")
(command "_.CIRCLE" (list 5500 2277) 5)
(command "-LAYER" "S" "Textos" "")
(command "-COLOR" "7")
(command "-TEXT" "S" "Standard" "J" "C" (list 5470 2255) 10 0 "2xTEL")
(command "-LAYER" "S" "TVs" "")
(command "-COLOR" "5")
(command "_.PLINE" (list 5480.0 2320) (list 5520.0 2320) (list 5520.0 2345) (list 5480.0 2345) "C")
(command "_.PLINE" (list 5490.0 2320) (list 5510.0 2320) (list 5500 2310) (list 5490.0 2320) "")
(command "-LAYER" "S" "Textos" "")
(command "-COLOR" "7")
(command "-TEXT" "S" "Standard" "J" "C" (list 5470 2335) 10 0 "7xTV")
(command "-LAYER" "S" "APs" "")
(command "-COLOR" "3")
(command "_.PLINE" (list 5490.0 3320) (list 5510.0 3320) (list 5500 3345) (list 5490.0 3320) "")
(command "_.CIRCLE" (list 5500 3345) 10)
(command "_.CIRCLE" (list 5500 3345) 21.25)
(command "_.CIRCLE" (list 5500 3345) 30)
(command "-LAYER" "S" "Textos" "")
(command "-COLOR" "7")
(command "-TEXT" "S" "Standard" "J" "C" (list 5470 3335) 10 0 "4xAP")
(command "-LAYER" "S" "Telefonos" "")
(command "-COLOR" "4")
(command "_.PLINE" (list 5490.0 3400) (list 5510.0 3400) (list 5510.0 3430) (list 5490.0 3430) "C")
(command "_.CIRCLE" (list 5500 3437) 5)
(command "-LAYER" "S" "Textos" "")
(command "-COLOR" "7")
(command "-TEXT" "S" "Standard" "J" "C" (list 5470 3415) 10 0 "2xTEL")
(command "-LAYER" "S" "TVs" "")
(command "-COLOR" "5")
(command "_.PLINE" (list 5480.0 3480) (list 5520.0 3480) (list 5520.0 3505) (list 5480.0 3505) "C")
(command "_.PLINE" (list 5490.0 3480) (list 5510.0 3480) (list 5500 3470) (list 5490.0 3480) "")
(command "-LAYER" "S" "Textos" "")
(command "-COLOR" "7")
(command "-TEXT" "S" "Standard" "J" "C" (list 5470 3495) 10 0 "7xTV")
(command "-LAYER" "S" "APs" "")
(command "-COLOR" "3")
(command "_.PLINE" (list 5490.0 4400) (list 5510.0 4400) (list 5500 4425) (list 5490.0 4400) "")
(command "_.CIRCLE" (list 5500 4425) 10)
(command "_.CIRCLE" (list 5500 4425) 21.25)
(command "_.CIRCLE" (list 5500 4425) 30)
(command "-LAYER" "S" "Textos" "")
(command "-COLOR" "7")
(command "-TEXT" "S" "Standard" "J" "C" (list 5470 4415) 10 0 "4xAP")
(command "-LAYER" "S" "Telefonos" "")
(command "-COLOR" "4")
(command "_.PLINE" (list 5490.0 4480) (list 5510.0 4480) (list 5510.0 4510) (list 5490.0 4510) "C")
(command "_.CIRCLE" (list 5500 4517) 5)
(command "-LAYER" "S" "Textos" "")
(command "-COLOR" "7")
(command "-TEXT" "S" "Standard" "J" "C" (list 5470 4495) 10 0 "2xTEL")
(command "-LAYER" "S" "TVs" "")
(command "-COLOR" "5")
(command "_.PLINE" (list 5480.0 4560) (list 5520.0 4560) (list 5520.0 4585) (list 5480.0 4585) "C")
(command "_.PLINE" (list 5490.0 4560) (list 5510.0 4560) (list 5500 4550) (list 5490.0 4560) "")
(command "-LAYER" "S" "Textos" "")
(command "-COLOR" "7")
(command "-TEXT" "S" "Standard" "J" "C" (list 5470 4575) 10 0 "6xTV")
(command "-LAYER" "S" "APs" "")
(command "-COLOR" "3")
(command "_.PLINE" (list 5490.0 5400) (list 5510.0 5400) (list 5500 5425) (list 5490.0 5400) "")
(command "_.CIRCLE" (list 5500 5425) 10)
(command "_.CIRCLE" (list 5500 5425) 21.25)
(command "_.CIRCLE" (list 5500 5425) 30)
(command "-LAYER" "S" "Textos" "")
(command "-COLOR" "7")
(command "-TEXT" "S" "Standard" "J" "C" (list 5470 5415) 10 0 "6xAP")
(command "-LAYER" "S" "Telefonos" "")
(command "-COLOR" "4")
(command "_.PLINE" (list 5490.0 5480) (list 5510.0 5480) (list 5510.0 5510) (list 5490.0 5510) "C")
(command "_.CIRCLE" (list 5500 5517) 5)
(command "-LAYER" "S" "Textos" "")
(command "-COLOR" "7")
(command "-TEXT" "S" "Standard" "J" "C" (list 5470 5495) 10 0 "3xTEL")
(command "-LAYER" "S" "TVs" "")
(command "-COLOR" "5")
(command "_.PLINE" (list 5480.0 5560) (list 5520.0 5560) (list 5520.0 5585) (list 5480.0 5585) "C")
(command "_.PLINE" (list 5490.0 5560) (list 5510.0 5560) (list 5500 5550) (list 5490.0 5560) "")
(command "-LAYER" "S" "Textos" "")
(command "-COLOR" "7")
(command "-TEXT" "S" "Standard" "J" "C" (list 5470 5575) 10 0 "9xTV")
(command "-LAYER" "S" "APs" "")
(command "-COLOR" "3")
(command "_.PLINE" (list 5490.0 7800) (list 5510.0 7800) (list 5500 7825) (list 5490.0 7800) "")
(command "_.CIRCLE" (list 5500 7825) 10)
(command "_.CIRCLE" (list 5500 7825) 21.25)
(command "_.CIRCLE" (list 5500 7825) 30)
(command "-LAYER" "S" "Textos" "")
(command "-COLOR" "7")
(command "-TEXT" "S" "Standard" "J" "C" (list 5470 7815) 10 0 "2xAP")
(command "-LAYER" "S" "Telefonos" "")
(command "-COLOR" "4")
(command "_.PLINE" (list 5490.0 7880) (list 5510.0 7880) (list 5510.0 7910) (list 5490.0 7910) "C")
(command "_.CIRCLE" (list 5500 7917) 5)
(command "-LAYER" "S" "Textos" "")
(command "-COLOR" "7")
(command "-TEXT" "S" "Standard" "J" "C" (list 5470 7895) 10 0 "1xTEL")
(command "-LAYER" "S" "TVs" "")
(command "-COLOR" "5")
(command "_.PLINE" (list 5480.0 7960) (list 5520.0 7960) (list 5520.0 7985) (list 5480.0 7985) "C")
(command "_.PLINE" (list 5490.0 7960) (list 5510.0 7960) (list 5500 7950) (list 5490.0 7960) "")
(command "-LAYER" "S" "Textos" "")
(command "-COLOR" "7")
(command "-TEXT" "S" "Standard" "J" "C" (list 5470 7975) 10 0 "3xTV")

; === DIBUJAR TORRE: IDF6 ===
(command "-LAYER" "S" "Textos" "")
(command "-COLOR" "7")
(command "-TEXT" "S" "Standard" "J" "C" (list 6400 150) 25 0 "IDF6")
(command "-LAYER" "S" "Switches" "")
(command "-COLOR" "6")
(command "_.PLINE" (list 6450 150) (list 6600 150) (list 6600 190) (list 6450 190) "C")
(command "-LAYER" "S" "Textos" "")
(command "-COLOR" "7")
(command "-TEXT" "S" "Standard" "J" "MC" (list 6525.0 170.0) 8 0 "SW-CCTV (DS-3E3728F)")
(command "-LAYER" "S" "Switches" "")
(command "-COLOR" "6")
(command "_.PLINE" (list 6450 250) (list 6600 250) (list 6600 290) (list 6450 290) "C")
(command "-LAYER" "S" "Textos" "")
(command "-COLOR" "7")
(command "-TEXT" "S" "Standard" "J" "MC" (list 6525.0 270.0) 8 0 "SW-DATA (Meraki MS225)")
(command "-LAYER" "S" "Switches" "")
(command "-COLOR" "6")
(command "_.PLINE" (list 6450 350) (list 6600 350) (list 6600 390) (list 6450 390) "C")
(command "-LAYER" "S" "Textos" "")
(command "-COLOR" "7")
(command "-TEXT" "S" "Standard" "J" "MC" (list 6525.0 370.0) 8 0 "SW-IPTV (RG-NBS6002)")
(command "-LAYER" "S" "Switches" "")
(command "-COLOR" "6")
(command "_.PLINE" (list 6450 450) (list 6600 450) (list 6600 490) (list 6450 490) "C")
(command "-LAYER" "S" "Textos" "")
(command "-COLOR" "7")
(command "-TEXT" "S" "Standard" "J" "MC" (list 6525.0 470.0) 8 0 "SW-TEL (Meraki MS225)")
(command "-LAYER" "S" "Switches" "")
(command "-COLOR" "6")
(command "_.PLINE" (list 6450 550) (list 6600 550) (list 6600 590) (list 6450 590) "C")
(command "-LAYER" "S" "Textos" "")
(command "-COLOR" "7")
(command "-TEXT" "S" "Standard" "J" "MC" (list 6525.0 570.0) 8 0 "SW-WIFI (Meraki MS225)")
(command "-LAYER" "S" "APs" "")
(command "-COLOR" "3")
(command "_.PLINE" (list 6540.0 840) (list 6560.0 840) (list 6550 865) (list 6540.0 840) "")
(command "_.CIRCLE" (list 6550 865) 10)
(command "_.CIRCLE" (list 6550 865) 21.25)
(command "_.CIRCLE" (list 6550 865) 30)
(command "-LAYER" "S" "Textos" "")
(command "-COLOR" "7")
(command "-TEXT" "S" "Standard" "J" "C" (list 6520 855) 10 0 "3xAP")
(command "-LAYER" "S" "Telefonos" "")
(command "-COLOR" "4")
(command "_.PLINE" (list 6540.0 920) (list 6560.0 920) (list 6560.0 950) (list 6540.0 950) "C")
(command "_.CIRCLE" (list 6550 957) 5)
(command "-LAYER" "S" "Textos" "")
(command "-COLOR" "7")
(command "-TEXT" "S" "Standard" "J" "C" (list 6520 935) 10 0 "1xTEL")
(command "-LAYER" "S" "TVs" "")
(command "-COLOR" "5")
(command "_.PLINE" (list 6530.0 1000) (list 6570.0 1000) (list 6570.0 1025) (list 6530.0 1025) "C")
(command "_.PLINE" (list 6540.0 1000) (list 6560.0 1000) (list 6550 990) (list 6540.0 1000) "")
(command "-LAYER" "S" "Textos" "")
(command "-COLOR" "7")
(command "-TEXT" "S" "Standard" "J" "C" (list 6520 1015) 10 0 "5xTV")
(command "-LAYER" "S" "APs" "")
(command "-COLOR" "3")
(command "_.PLINE" (list 6540.0 2160) (list 6560.0 2160) (list 6550 2185) (list 6540.0 2160) "")
(command "_.CIRCLE" (list 6550 2185) 10)
(command "_.CIRCLE" (list 6550 2185) 21.25)
(command "_.CIRCLE" (list 6550 2185) 30)
(command "-LAYER" "S" "Textos" "")
(command "-COLOR" "7")
(command "-TEXT" "S" "Standard" "J" "C" (list 6520 2175) 10 0 "6xAP")
(command "-LAYER" "S" "Telefonos" "")
(command "-COLOR" "4")
(command "_.PLINE" (list 6540.0 2240) (list 6560.0 2240) (list 6560.0 2270) (list 6540.0 2270) "C")
(command "_.CIRCLE" (list 6550 2277) 5)
(command "-LAYER" "S" "Textos" "")
(command "-COLOR" "7")
(command "-TEXT" "S" "Standard" "J" "C" (list 6520 2255) 10 0 "3xTEL")
(command "-LAYER" "S" "TVs" "")
(command "-COLOR" "5")
(command "_.PLINE" (list 6530.0 2320) (list 6570.0 2320) (list 6570.0 2345) (list 6530.0 2345) "C")
(command "_.PLINE" (list 6540.0 2320) (list 6560.0 2320) (list 6550 2310) (list 6540.0 2320) "")
(command "-LAYER" "S" "Textos" "")
(command "-COLOR" "7")
(command "-TEXT" "S" "Standard" "J" "C" (list 6520 2335) 10 0 "10xTV")
(command "-LAYER" "S" "APs" "")
(command "-COLOR" "3")
(command "_.PLINE" (list 6540.0 3320) (list 6560.0 3320) (list 6550 3345) (list 6540.0 3320) "")
(command "_.CIRCLE" (list 6550 3345) 10)
(command "_.CIRCLE" (list 6550 3345) 21.25)
(command "_.CIRCLE" (list 6550 3345) 30)
(command "-LAYER" "S" "Textos" "")
(command "-COLOR" "7")
(command "-TEXT" "S" "Standard" "J" "C" (list 6520 3335) 10 0 "4xAP")
(command "-LAYER" "S" "Telefonos" "")
(command "-COLOR" "4")
(command "_.PLINE" (list 6540.0 3400) (list 6560.0 3400) (list 6560.0 3430) (list 6540.0 3430) "C")
(command "_.CIRCLE" (list 6550 3437) 5)
(command "-LAYER" "S" "Textos" "")
(command "-COLOR" "7")
(command "-TEXT" "S" "Standard" "J" "C" (list 6520 3415) 10 0 "2xTEL")
(command "-LAYER" "S" "TVs" "")
(command "-COLOR" "5")
(command "_.PLINE" (list 6530.0 3480) (list 6570.0 3480) (list 6570.0 3505) (list 6530.0 3505) "C")
(command "_.PLINE" (list 6540.0 3480) (list 6560.0 3480) (list 6550 3470) (list 6540.0 3480) "")
(command "-LAYER" "S" "Textos" "")
(command "-COLOR" "7")
(command "-TEXT" "S" "Standard" "J" "C" (list 6520 3495) 10 0 "7xTV")
(command "-LAYER" "S" "APs" "")
(command "-COLOR" "3")
(command "_.PLINE" (list 6540.0 5400) (list 6560.0 5400) (list 6550 5425) (list 6540.0 5400) "")
(command "_.CIRCLE" (list 6550 5425) 10)
(command "_.CIRCLE" (list 6550 5425) 21.25)
(command "_.CIRCLE" (list 6550 5425) 30)
(command "-LAYER" "S" "Textos" "")
(command "-COLOR" "7")
(command "-TEXT" "S" "Standard" "J" "C" (list 6520 5415) 10 0 "2xAP")
(command "-LAYER" "S" "Telefonos" "")
(command "-COLOR" "4")
(command "_.PLINE" (list 6540.0 5480) (list 6560.0 5480) (list 6560.0 5510) (list 6540.0 5510) "C")
(command "_.CIRCLE" (list 6550 5517) 5)
(command "-LAYER" "S" "Textos" "")
(command "-COLOR" "7")
(command "-TEXT" "S" "Standard" "J" "C" (list 6520 5495) 10 0 "1xTEL")
(command "-LAYER" "S" "TVs" "")
(command "-COLOR" "5")
(command "_.PLINE" (list 6530.0 5560) (list 6570.0 5560) (list 6570.0 5585) (list 6530.0 5585) "C")
(command "_.PLINE" (list 6540.0 5560) (list 6560.0 5560) (list 6550 5550) (list 6540.0 5560) "")
(command "-LAYER" "S" "Textos" "")
(command "-COLOR" "7")
(command "-TEXT" "S" "Standard" "J" "C" (list 6520 5575) 10 0 "3xTV")
(command "-LAYER" "S" "APs" "")
(command "-COLOR" "3")
(command "_.PLINE" (list 6540.0 6560) (list 6560.0 6560) (list 6550 6585) (list 6540.0 6560) "")
(command "_.CIRCLE" (list 6550 6585) 10)
(command "_.CIRCLE" (list 6550 6585) 21.25)
(command "_.CIRCLE" (list 6550 6585) 30)
(command "-LAYER" "S" "Textos" "")
(command "-COLOR" "7")
(command "-TEXT" "S" "Standard" "J" "C" (list 6520 6575) 10 0 "4xAP")
(command "-LAYER" "S" "Telefonos" "")
(command "-COLOR" "4")
(command "_.PLINE" (list 6540.0 6640) (list 6560.0 6640) (list 6560.0 6670) (list 6540.0 6670) "C")
(command "_.CIRCLE" (list 6550 6677) 5)
(command "-LAYER" "S" "Textos" "")
(command "-COLOR" "7")
(command "-TEXT" "S" "Standard" "J" "C" (list 6520 6655) 10 0 "2xTEL")
(command "-LAYER" "S" "TVs" "")
(command "-COLOR" "5")
(command "_.PLINE" (list 6530.0 6720) (list 6570.0 6720) (list 6570.0 6745) (list 6530.0 6745) "C")
(command "_.PLINE" (list 6540.0 6720) (list 6560.0 6720) (list 6550 6710) (list 6540.0 6720) "")
(command "-LAYER" "S" "Textos" "")
(command "-COLOR" "7")
(command "-TEXT" "S" "Standard" "J" "C" (list 6520 6735) 10 0 "7xTV")
(command "-LAYER" "S" "APs" "")
(command "-COLOR" "3")
(command "_.PLINE" (list 6540.0 7800) (list 6560.0 7800) (list 6550 7825) (list 6540.0 7800) "")
(command "_.CIRCLE" (list 6550 7825) 10)
(command "_.CIRCLE" (list 6550 7825) 21.25)
(command "_.CIRCLE" (list 6550 7825) 30)
(command "-LAYER" "S" "Textos" "")
(command "-COLOR" "7")
(command "-TEXT" "S" "Standard" "J" "C" (list 6520 7815) 10 0 "4xAP")
(command "-LAYER" "S" "Telefonos" "")
(command "-COLOR" "4")
(command "_.PLINE" (list 6540.0 7880) (list 6560.0 7880) (list 6560.0 7910) (list 6540.0 7910) "C")
(command "_.CIRCLE" (list 6550 7917) 5)
(command "-LAYER" "S" "Textos" "")
(command "-COLOR" "7")
(command "-TEXT" "S" "Standard" "J" "C" (list 6520 7895) 10 0 "2xTEL")
(command "-LAYER" "S" "TVs" "")
(command "-COLOR" "5")
(command "_.PLINE" (list 6530.0 7960) (list 6570.0 7960) (list 6570.0 7985) (list 6530.0 7985) "C")
(command "_.PLINE" (list 6540.0 7960) (list 6560.0 7960) (list 6550 7950) (list 6540.0 7960) "")
(command "-LAYER" "S" "Textos" "")
(command "-COLOR" "7")
(command "-TEXT" "S" "Standard" "J" "C" (list 6520 7975) 10 0 "8xTV")

; === DIBUJAR TORRE: IDF7 ===
(command "-LAYER" "S" "Textos" "")
(command "-COLOR" "7")
(command "-TEXT" "S" "Standard" "J" "C" (list 7450 150) 25 0 "IDF7")
(command "-LAYER" "S" "Switches" "")
(command "-COLOR" "6")
(command "_.PLINE" (list 7500 150) (list 7650 150) (list 7650 190) (list 7500 190) "C")
(command "-LAYER" "S" "Textos" "")
(command "-COLOR" "7")
(command "-TEXT" "S" "Standard" "J" "MC" (list 7575.0 170.0) 8 0 "SW-CCTV (DS-3E3728F)")
(command "-LAYER" "S" "Switches" "")
(command "-COLOR" "6")
(command "_.PLINE" (list 7500 250) (list 7650 250) (list 7650 290) (list 7500 290) "C")
(command "-LAYER" "S" "Textos" "")
(command "-COLOR" "7")
(command "-TEXT" "S" "Standard" "J" "MC" (list 7575.0 270.0) 8 0 "SW-DATA (Meraki MS225)")
(command "-LAYER" "S" "Switches" "")
(command "-COLOR" "6")
(command "_.PLINE" (list 7500 350) (list 7650 350) (list 7650 390) (list 7500 390) "C")
(command "-LAYER" "S" "Textos" "")
(command "-COLOR" "7")
(command "-TEXT" "S" "Standard" "J" "MC" (list 7575.0 370.0) 8 0 "SW-IPTV (RG-NBS6002)")
(command "-LAYER" "S" "Switches" "")
(command "-COLOR" "6")
(command "_.PLINE" (list 7500 450) (list 7650 450) (list 7650 490) (list 7500 490) "C")
(command "-LAYER" "S" "Textos" "")
(command "-COLOR" "7")
(command "-TEXT" "S" "Standard" "J" "MC" (list 7575.0 470.0) 8 0 "SW-TEL (Meraki MS225)")
(command "-LAYER" "S" "Switches" "")
(command "-COLOR" "6")
(command "_.PLINE" (list 7500 550) (list 7650 550) (list 7650 590) (list 7500 590) "C")
(command "-LAYER" "S" "Textos" "")
(command "-COLOR" "7")
(command "-TEXT" "S" "Standard" "J" "MC" (list 7575.0 570.0) 8 0 "SW-WIFI (Meraki MS225)")
(command "-LAYER" "S" "APs" "")
(command "-COLOR" "3")
(command "_.PLINE" (list 7590.0 840) (list 7610.0 840) (list 7600 865) (list 7590.0 840) "")
(command "_.CIRCLE" (list 7600 865) 10)
(command "_.CIRCLE" (list 7600 865) 21.25)
(command "_.CIRCLE" (list 7600 865) 30)
(command "-LAYER" "S" "Textos" "")
(command "-COLOR" "7")
(command "-TEXT" "S" "Standard" "J" "C" (list 7570 855) 10 0 "6xAP")
(command "-LAYER" "S" "Telefonos" "")
(command "-COLOR" "4")
(command "_.PLINE" (list 7590.0 920) (list 7610.0 920) (list 7610.0 950) (list 7590.0 950) "C")
(command "_.CIRCLE" (list 7600 957) 5)
(command "-LAYER" "S" "Textos" "")
(command "-COLOR" "7")
(command "-TEXT" "S" "Standard" "J" "C" (list 7570 935) 10 0 "3xTEL")
(command "-LAYER" "S" "TVs" "")
(command "-COLOR" "5")
(command "_.PLINE" (list 7580.0 1000) (list 7620.0 1000) (list 7620.0 1025) (list 7580.0 1025) "C")
(command "_.PLINE" (list 7590.0 1000) (list 7610.0 1000) (list 7600 990) (list 7590.0 1000) "")
(command "-LAYER" "S" "Textos" "")
(command "-COLOR" "7")
(command "-TEXT" "S" "Standard" "J" "C" (list 7570 1015) 10 0 "10xTV")
(command "-LAYER" "S" "APs" "")
(command "-COLOR" "3")
(command "_.PLINE" (list 7590.0 4400) (list 7610.0 4400) (list 7600 4425) (list 7590.0 4400) "")
(command "_.CIRCLE" (list 7600 4425) 10)
(command "_.CIRCLE" (list 7600 4425) 21.25)
(command "_.CIRCLE" (list 7600 4425) 30)
(command "-LAYER" "S" "Textos" "")
(command "-COLOR" "7")
(command "-TEXT" "S" "Standard" "J" "C" (list 7570 4415) 10 0 "2xAP")
(command "-LAYER" "S" "Telefonos" "")
(command "-COLOR" "4")
(command "_.PLINE" (list 7590.0 4480) (list 7610.0 4480) (list 7610.0 4510) (list 7590.0 4510) "C")
(command "_.CIRCLE" (list 7600 4517) 5)
(command "-LAYER" "S" "Textos" "")
(command "-COLOR" "7")
(command "-TEXT" "S" "Standard" "J" "C" (list 7570 4495) 10 0 "1xTEL")
(command "-LAYER" "S" "TVs" "")
(command "-COLOR" "5")
(command "_.PLINE" (list 7580.0 4560) (list 7620.0 4560) (list 7620.0 4585) (list 7580.0 4585) "C")
(command "_.PLINE" (list 7590.0 4560) (list 7610.0 4560) (list 7600 4550) (list 7590.0 4560) "")
(command "-LAYER" "S" "Textos" "")
(command "-COLOR" "7")
(command "-TEXT" "S" "Standard" "J" "C" (list 7570 4575) 10 0 "3xTV")
(command "-LAYER" "S" "APs" "")
(command "-COLOR" "3")
(command "_.PLINE" (list 7590.0 5400) (list 7610.0 5400) (list 7600 5425) (list 7590.0 5400) "")
(command "_.CIRCLE" (list 7600 5425) 10)
(command "_.CIRCLE" (list 7600 5425) 21.25)
(command "_.CIRCLE" (list 7600 5425) 30)
(command "-LAYER" "S" "Textos" "")
(command "-COLOR" "7")
(command "-TEXT" "S" "Standard" "J" "C" (list 7570 5415) 10 0 "2xAP")
(command "-LAYER" "S" "Telefonos" "")
(command "-COLOR" "4")
(command "_.PLINE" (list 7590.0 5480) (list 7610.0 5480) (list 7610.0 5510) (list 7590.0 5510) "C")
(command "_.CIRCLE" (list 7600 5517) 5)
(command "-LAYER" "S" "Textos" "")
(command "-COLOR" "7")
(command "-TEXT" "S" "Standard" "J" "C" (list 7570 5495) 10 0 "1xTEL")
(command "-LAYER" "S" "TVs" "")
(command "-COLOR" "5")
(command "_.PLINE" (list 7580.0 5560) (list 7620.0 5560) (list 7620.0 5585) (list 7580.0 5585) "C")
(command "_.PLINE" (list 7590.0 5560) (list 7610.0 5560) (list 7600 5550) (list 7590.0 5560) "")
(command "-LAYER" "S" "Textos" "")
(command "-COLOR" "7")
(command "-TEXT" "S" "Standard" "J" "C" (list 7570 5575) 10 0 "3xTV")
(command "-LAYER" "S" "APs" "")
(command "-COLOR" "3")
(command "_.PLINE" (list 7590.0 6560) (list 7610.0 6560) (list 7600 6585) (list 7590.0 6560) "")
(command "_.CIRCLE" (list 7600 6585) 10)
(command "_.CIRCLE" (list 7600 6585) 21.25)
(command "_.CIRCLE" (list 7600 6585) 30)
(command "-LAYER" "S" "Textos" "")
(command "-COLOR" "7")
(command "-TEXT" "S" "Standard" "J" "C" (list 7570 6575) 10 0 "4xAP")
(command "-LAYER" "S" "Telefonos" "")
(command "-COLOR" "4")
(command "_.PLINE" (list 7590.0 6640) (list 7610.0 6640) (list 7610.0 6670) (list 7590.0 6670) "C")
(command "_.CIRCLE" (list 7600 6677) 5)
(command "-LAYER" "S" "Textos" "")
(command "-COLOR" "7")
(command "-TEXT" "S" "Standard" "J" "C" (list 7570 6655) 10 0 "2xTEL")
(command "-LAYER" "S" "TVs" "")
(command "-COLOR" "5")
(command "_.PLINE" (list 7580.0 6720) (list 7620.0 6720) (list 7620.0 6745) (list 7580.0 6745) "C")
(command "_.PLINE" (list 7590.0 6720) (list 7610.0 6720) (list 7600 6710) (list 7590.0 6720) "")
(command "-LAYER" "S" "Textos" "")
(command "-COLOR" "7")
(command "-TEXT" "S" "Standard" "J" "C" (list 7570 6735) 10 0 "7xTV")
(command "-LAYER" "S" "APs" "")
(command "-COLOR" "3")
(command "_.PLINE" (list 7590.0 7800) (list 7610.0 7800) (list 7600 7825) (list 7590.0 7800) "")
(command "_.CIRCLE" (list 7600 7825) 10)
(command "_.CIRCLE" (list 7600 7825) 21.25)
(command "_.CIRCLE" (list 7600 7825) 30)
(command "-LAYER" "S" "Textos" "")
(command "-COLOR" "7")
(command "-TEXT" "S" "Standard" "J" "C" (list 7570 7815) 10 0 "8xAP")
(command "-LAYER" "S" "Telefonos" "")
(command "-COLOR" "4")
(command "_.PLINE" (list 7590.0 7880) (list 7610.0 7880) (list 7610.0 7910) (list 7590.0 7910) "C")
(command "_.CIRCLE" (list 7600 7917) 5)
(command "-LAYER" "S" "Textos" "")
(command "-COLOR" "7")
(command "-TEXT" "S" "Standard" "J" "C" (list 7570 7895) 10 0 "4xTEL")
(command "-LAYER" "S" "TVs" "")
(command "-COLOR" "5")
(command "_.PLINE" (list 7580.0 7960) (list 7620.0 7960) (list 7620.0 7985) (list 7580.0 7985) "C")
(command "_.PLINE" (list 7590.0 7960) (list 7610.0 7960) (list 7600 7950) (list 7590.0 7960) "")
(command "-LAYER" "S" "Textos" "")
(command "-COLOR" "7")
(command "-TEXT" "S" "Standard" "J" "C" (list 7570 7975) 10 0 "13xTV")

; === DIBUJAR TORRE: IDF8 ===
(command "-LAYER" "S" "Textos" "")
(command "-COLOR" "7")
(command "-TEXT" "S" "Standard" "J" "C" (list 8500 150) 25 0 "IDF8")
(command "-LAYER" "S" "Switches" "")
(command "-COLOR" "6")
(command "_.PLINE" (list 8550 150) (list 8700 150) (list 8700 190) (list 8550 190) "C")
(command "-LAYER" "S" "Textos" "")
(command "-COLOR" "7")
(command "-TEXT" "S" "Standard" "J" "MC" (list 8625.0 170.0) 8 0 "SW-CCTV (DS-3E3728F)")
(command "-LAYER" "S" "Switches" "")
(command "-COLOR" "6")
(command "_.PLINE" (list 8550 250) (list 8700 250) (list 8700 290) (list 8550 290) "C")
(command "-LAYER" "S" "Textos" "")
(command "-COLOR" "7")
(command "-TEXT" "S" "Standard" "J" "MC" (list 8625.0 270.0) 8 0 "SW-DATA (Meraki MS225)")
(command "-LAYER" "S" "Switches" "")
(command "-COLOR" "6")
(command "_.PLINE" (list 8550 350) (list 8700 350) (list 8700 390) (list 8550 390) "C")
(command "-LAYER" "S" "Textos" "")
(command "-COLOR" "7")
(command "-TEXT" "S" "Standard" "J" "MC" (list 8625.0 370.0) 8 0 "SW-IPTV (RG-NBS6002)")
(command "-LAYER" "S" "Switches" "")
(command "-COLOR" "6")
(command "_.PLINE" (list 8550 450) (list 8700 450) (list 8700 490) (list 8550 490) "C")
(command "-LAYER" "S" "Textos" "")
(command "-COLOR" "7")
(command "-TEXT" "S" "Standard" "J" "MC" (list 8625.0 470.0) 8 0 "SW-TEL (Meraki MS225)")
(command "-LAYER" "S" "Switches" "")
(command "-COLOR" "6")
(command "_.PLINE" (list 8550 550) (list 8700 550) (list 8700 590) (list 8550 590) "C")
(command "-LAYER" "S" "Textos" "")
(command "-COLOR" "7")
(command "-TEXT" "S" "Standard" "J" "MC" (list 8625.0 570.0) 8 0 "SW-WIFI (Meraki MS225)")
(command "-LAYER" "S" "APs" "")
(command "-COLOR" "3")
(command "_.PLINE" (list 8640.0 840) (list 8660.0 840) (list 8650 865) (list 8640.0 840) "")
(command "_.CIRCLE" (list 8650 865) 10)
(command "_.CIRCLE" (list 8650 865) 21.25)
(command "_.CIRCLE" (list 8650 865) 30)
(command "-LAYER" "S" "Textos" "")
(command "-COLOR" "7")
(command "-TEXT" "S" "Standard" "J" "C" (list 8620 855) 10 0 "4xAP")
(command "-LAYER" "S" "Telefonos" "")
(command "-COLOR" "4")
(command "_.PLINE" (list 8640.0 920) (list 8660.0 920) (list 8660.0 950) (list 8640.0 950) "C")
(command "_.CIRCLE" (list 8650 957) 5)
(command "-LAYER" "S" "Textos" "")
(command "-COLOR" "7")
(command "-TEXT" "S" "Standard" "J" "C" (list 8620 935) 10 0 "2xTEL")
(command "-LAYER" "S" "TVs" "")
(command "-COLOR" "5")
(command "_.PLINE" (list 8630.0 1000) (list 8670.0 1000) (list 8670.0 1025) (list 8630.0 1025) "C")
(command "_.PLINE" (list 8640.0 1000) (list 8660.0 1000) (list 8650 990) (list 8640.0 1000) "")
(command "-LAYER" "S" "Textos" "")
(command "-COLOR" "7")
(command "-TEXT" "S" "Standard" "J" "C" (list 8620 1015) 10 0 "6xTV")
(command "-LAYER" "S" "APs" "")
(command "-COLOR" "3")
(command "_.PLINE" (list 8640.0 2160) (list 8660.0 2160) (list 8650 2185) (list 8640.0 2160) "")
(command "_.CIRCLE" (list 8650 2185) 10)
(command "_.CIRCLE" (list 8650 2185) 21.25)
(command "_.CIRCLE" (list 8650 2185) 30)
(command "-LAYER" "S" "Textos" "")
(command "-COLOR" "7")
(command "-TEXT" "S" "Standard" "J" "C" (list 8620 2175) 10 0 "2xAP")
(command "-LAYER" "S" "Telefonos" "")
(command "-COLOR" "4")
(command "_.PLINE" (list 8640.0 2240) (list 8660.0 2240) (list 8660.0 2270) (list 8640.0 2270) "C")
(command "_.CIRCLE" (list 8650 2277) 5)
(command "-LAYER" "S" "Textos" "")
(command "-COLOR" "7")
(command "-TEXT" "S" "Standard" "J" "C" (list 8620 2255) 10 0 "1xTEL")
(command "-LAYER" "S" "TVs" "")
(command "-COLOR" "5")
(command "_.PLINE" (list 8630.0 2320) (list 8670.0 2320) (list 8670.0 2345) (list 8630.0 2345) "C")
(command "_.PLINE" (list 8640.0 2320) (list 8660.0 2320) (list 8650 2310) (list 8640.0 2320) "")
(command "-LAYER" "S" "Textos" "")
(command "-COLOR" "7")
(command "-TEXT" "S" "Standard" "J" "C" (list 8620 2335) 10 0 "3xTV")
(command "-LAYER" "S" "APs" "")
(command "-COLOR" "3")
(command "_.PLINE" (list 8640.0 3320) (list 8660.0 3320) (list 8650 3345) (list 8640.0 3320) "")
(command "_.CIRCLE" (list 8650 3345) 10)
(command "_.CIRCLE" (list 8650 3345) 21.25)
(command "_.CIRCLE" (list 8650 3345) 30)
(command "-LAYER" "S" "Textos" "")
(command "-COLOR" "7")
(command "-TEXT" "S" "Standard" "J" "C" (list 8620 3335) 10 0 "8xAP")
(command "-LAYER" "S" "Telefonos" "")
(command "-COLOR" "4")
(command "_.PLINE" (list 8640.0 3400) (list 8660.0 3400) (list 8660.0 3430) (list 8640.0 3430) "C")
(command "_.CIRCLE" (list 8650 3437) 5)
(command "-LAYER" "S" "Textos" "")
(command "-COLOR" "7")
(command "-TEXT" "S" "Standard" "J" "C" (list 8620 3415) 10 0 "4xTEL")
(command "-LAYER" "S" "TVs" "")
(command "-COLOR" "5")
(command "_.PLINE" (list 8630.0 3480) (list 8670.0 3480) (list 8670.0 3505) (list 8630.0 3505) "C")
(command "_.PLINE" (list 8640.0 3480) (list 8660.0 3480) (list 8650 3470) (list 8640.0 3480) "")
(command "-LAYER" "S" "Textos" "")
(command "-COLOR" "7")
(command "-TEXT" "S" "Standard" "J" "C" (list 8620 3495) 10 0 "12xTV")
(command "-LAYER" "S" "APs" "")
(command "-COLOR" "3")
(command "_.PLINE" (list 8640.0 5400) (list 8660.0 5400) (list 8650 5425) (list 8640.0 5400) "")
(command "_.CIRCLE" (list 8650 5425) 10)
(command "_.CIRCLE" (list 8650 5425) 21.25)
(command "_.CIRCLE" (list 8650 5425) 30)
(command "-LAYER" "S" "Textos" "")
(command "-COLOR" "7")
(command "-TEXT" "S" "Standard" "J" "C" (list 8620 5415) 10 0 "3xAP")
(command "-LAYER" "S" "Telefonos" "")
(command "-COLOR" "4")
(command "_.PLINE" (list 8640.0 5480) (list 8660.0 5480) (list 8660.0 5510) (list 8640.0 5510) "C")
(command "_.CIRCLE" (list 8650 5517) 5)
(command "-LAYER" "S" "Textos" "")
(command "-COLOR" "7")
(command "-TEXT" "S" "Standard" "J" "C" (list 8620 5495) 10 0 "1xTEL")
(command "-LAYER" "S" "TVs" "")
(command "-COLOR" "5")
(command "_.PLINE" (list 8630.0 5560) (list 8670.0 5560) (list 8670.0 5585) (list 8630.0 5585) "C")
(command "_.PLINE" (list 8640.0 5560) (list 8660.0 5560) (list 8650 5550) (list 8640.0 5560) "")
(command "-LAYER" "S" "Textos" "")
(command "-COLOR" "7")
(command "-TEXT" "S" "Standard" "J" "C" (list 8620 5575) 10 0 "5xTV")
(command "-LAYER" "S" "APs" "")
(command "-COLOR" "3")
(command "_.PLINE" (list 8640.0 6560) (list 8660.0 6560) (list 8650 6585) (list 8640.0 6560) "")
(command "_.CIRCLE" (list 8650 6585) 10)
(command "_.CIRCLE" (list 8650 6585) 21.25)
(command "_.CIRCLE" (list 8650 6585) 30)
(command "-LAYER" "S" "Textos" "")
(command "-COLOR" "7")
(command "-TEXT" "S" "Standard" "J" "C" (list 8620 6575) 10 0 "4xAP")
(command "-LAYER" "S" "Telefonos" "")
(command "-COLOR" "4")
(command "_.PLINE" (list 8640.0 6640) (list 8660.0 6640) (list 8660.0 6670) (list 8640.0 6670) "C")
(command "_.CIRCLE" (list 8650 6677) 5)
(command "-LAYER" "S" "Textos" "")
(command "-COLOR" "7")
(command "-TEXT" "S" "Standard" "J" "C" (list 8620 6655) 10 0 "2xTEL")
(command "-LAYER" "S" "TVs" "")
(command "-COLOR" "5")
(command "_.PLINE" (list 8630.0 6720) (list 8670.0 6720) (list 8670.0 6745) (list 8630.0 6745) "C")
(command "_.PLINE" (list 8640.0 6720) (list 8660.0 6720) (list 8650 6710) (list 8640.0 6720) "")
(command "-LAYER" "S" "Textos" "")
(command "-COLOR" "7")
(command "-TEXT" "S" "Standard" "J" "C" (list 8620 6735) 10 0 "7xTV")
(command "-LAYER" "S" "APs" "")
(command "-COLOR" "3")
(command "_.PLINE" (list 8640.0 7800) (list 8660.0 7800) (list 8650 7825) (list 8640.0 7800) "")
(command "_.CIRCLE" (list 8650 7825) 10)
(command "_.CIRCLE" (list 8650 7825) 21.25)
(command "_.CIRCLE" (list 8650 7825) 30)
(command "-LAYER" "S" "Textos" "")
(command "-COLOR" "7")
(command "-TEXT" "S" "Standard" "J" "C" (list 8620 7815) 10 0 "3xAP")
(command "-LAYER" "S" "Telefonos" "")
(command "-COLOR" "4")
(command "_.PLINE" (list 8640.0 7880) (list 8660.0 7880) (list 8660.0 7910) (list 8640.0 7910) "C")
(command "_.CIRCLE" (list 8650 7917) 5)
(command "-LAYER" "S" "Textos" "")
(command "-COLOR" "7")
(command "-TEXT" "S" "Standard" "J" "C" (list 8620 7895) 10 0 "1xTEL")
(command "-LAYER" "S" "TVs" "")
(command "-COLOR" "5")
(command "_.PLINE" (list 8630.0 7960) (list 8670.0 7960) (list 8670.0 7985) (list 8630.0 7985) "C")
(command "_.PLINE" (list 8640.0 7960) (list 8660.0 7960) (list 8650 7950) (list 8640.0 7960) "")
(command "-LAYER" "S" "Textos" "")
(command "-COLOR" "7")
(command "-TEXT" "S" "Standard" "J" "C" (list 8620 7975) 10 0 "5xTV")

; === DIBUJAR TORRE: IDF9 ===
(command "-LAYER" "S" "Textos" "")
(command "-COLOR" "7")
(command "-TEXT" "S" "Standard" "J" "C" (list 9550 150) 25 0 "IDF9")
(command "-LAYER" "S" "Switches" "")
(command "-COLOR" "6")
(command "_.PLINE" (list 9600 150) (list 9750 150) (list 9750 190) (list 9600 190) "C")
(command "-LAYER" "S" "Textos" "")
(command "-COLOR" "7")
(command "-TEXT" "S" "Standard" "J" "MC" (list 9675.0 170.0) 8 0 "SW-CCTV (DS-3E3728F)")
(command "-LAYER" "S" "Switches" "")
(command "-COLOR" "6")
(command "_.PLINE" (list 9600 250) (list 9750 250) (list 9750 290) (list 9600 290) "C")
(command "-LAYER" "S" "Textos" "")
(command "-COLOR" "7")
(command "-TEXT" "S" "Standard" "J" "MC" (list 9675.0 270.0) 8 0 "SW-DATA (Meraki MS225)")
(command "-LAYER" "S" "Switches" "")
(command "-COLOR" "6")
(command "_.PLINE" (list 9600 350) (list 9750 350) (list 9750 390) (list 9600 390) "C")
(command "-LAYER" "S" "Textos" "")
(command "-COLOR" "7")
(command "-TEXT" "S" "Standard" "J" "MC" (list 9675.0 370.0) 8 0 "SW-IPTV (RG-NBS6002)")
(command "-LAYER" "S" "Switches" "")
(command "-COLOR" "6")
(command "_.PLINE" (list 9600 450) (list 9750 450) (list 9750 490) (list 9600 490) "C")
(command "-LAYER" "S" "Textos" "")
(command "-COLOR" "7")
(command "-TEXT" "S" "Standard" "J" "MC" (list 9675.0 470.0) 8 0 "SW-TEL (Meraki MS225)")
(command "-LAYER" "S" "Switches" "")
(command "-COLOR" "6")
(command "_.PLINE" (list 9600 550) (list 9750 550) (list 9750 590) (list 9600 590) "C")
(command "-LAYER" "S" "Textos" "")
(command "-COLOR" "7")
(command "-TEXT" "S" "Standard" "J" "MC" (list 9675.0 570.0) 8 0 "SW-WIFI (Meraki MS225)")
(command "-LAYER" "S" "APs" "")
(command "-COLOR" "3")
(command "_.PLINE" (list 9690.0 840) (list 9710.0 840) (list 9700 865) (list 9690.0 840) "")
(command "_.CIRCLE" (list 9700 865) 10)
(command "_.CIRCLE" (list 9700 865) 21.25)
(command "_.CIRCLE" (list 9700 865) 30)
(command "-LAYER" "S" "Textos" "")
(command "-COLOR" "7")
(command "-TEXT" "S" "Standard" "J" "C" (list 9670 855) 10 0 "4xAP")
(command "-LAYER" "S" "Telefonos" "")
(command "-COLOR" "4")
(command "_.PLINE" (list 9690.0 920) (list 9710.0 920) (list 9710.0 950) (list 9690.0 950) "C")
(command "_.CIRCLE" (list 9700 957) 5)
(command "-LAYER" "S" "Textos" "")
(command "-COLOR" "7")
(command "-TEXT" "S" "Standard" "J" "C" (list 9670 935) 10 0 "2xTEL")
(command "-LAYER" "S" "TVs" "")
(command "-COLOR" "5")
(command "_.PLINE" (list 9680.0 1000) (list 9720.0 1000) (list 9720.0 1025) (list 9680.0 1025) "C")
(command "_.PLINE" (list 9690.0 1000) (list 9710.0 1000) (list 9700 990) (list 9690.0 1000) "")
(command "-LAYER" "S" "Textos" "")
(command "-COLOR" "7")
(command "-TEXT" "S" "Standard" "J" "C" (list 9670 1015) 10 0 "7xTV")
(command "-LAYER" "S" "APs" "")
(command "-COLOR" "3")
(command "_.PLINE" (list 9690.0 2160) (list 9710.0 2160) (list 9700 2185) (list 9690.0 2160) "")
(command "_.CIRCLE" (list 9700 2185) 10)
(command "_.CIRCLE" (list 9700 2185) 21.25)
(command "_.CIRCLE" (list 9700 2185) 30)
(command "-LAYER" "S" "Textos" "")
(command "-COLOR" "7")
(command "-TEXT" "S" "Standard" "J" "C" (list 9670 2175) 10 0 "2xAP")
(command "-LAYER" "S" "Telefonos" "")
(command "-COLOR" "4")
(command "_.PLINE" (list 9690.0 2240) (list 9710.0 2240) (list 9710.0 2270) (list 9690.0 2270) "C")
(command "_.CIRCLE" (list 9700 2277) 5)
(command "-LAYER" "S" "Textos" "")
(command "-COLOR" "7")
(command "-TEXT" "S" "Standard" "J" "C" (list 9670 2255) 10 0 "1xTEL")
(command "-LAYER" "S" "TVs" "")
(command "-COLOR" "5")
(command "_.PLINE" (list 9680.0 2320) (list 9720.0 2320) (list 9720.0 2345) (list 9680.0 2345) "C")
(command "_.PLINE" (list 9690.0 2320) (list 9710.0 2320) (list 9700 2310) (list 9690.0 2320) "")
(command "-LAYER" "S" "Textos" "")
(command "-COLOR" "7")
(command "-TEXT" "S" "Standard" "J" "C" (list 9670 2335) 10 0 "3xTV")
(command "-LAYER" "S" "APs" "")
(command "-COLOR" "3")
(command "_.PLINE" (list 9690.0 3320) (list 9710.0 3320) (list 9700 3345) (list 9690.0 3320) "")
(command "_.CIRCLE" (list 9700 3345) 10)
(command "_.CIRCLE" (list 9700 3345) 21.25)
(command "_.CIRCLE" (list 9700 3345) 30)
(command "-LAYER" "S" "Textos" "")
(command "-COLOR" "7")
(command "-TEXT" "S" "Standard" "J" "C" (list 9670 3335) 10 0 "4xAP")
(command "-LAYER" "S" "Telefonos" "")
(command "-COLOR" "4")
(command "_.PLINE" (list 9690.0 3400) (list 9710.0 3400) (list 9710.0 3430) (list 9690.0 3430) "C")
(command "_.CIRCLE" (list 9700 3437) 5)
(command "-LAYER" "S" "Textos" "")
(command "-COLOR" "7")
(command "-TEXT" "S" "Standard" "J" "C" (list 9670 3415) 10 0 "2xTEL")
(command "-LAYER" "S" "TVs" "")
(command "-COLOR" "5")
(command "_.PLINE" (list 9680.0 3480) (list 9720.0 3480) (list 9720.0 3505) (list 9680.0 3505) "C")
(command "_.PLINE" (list 9690.0 3480) (list 9710.0 3480) (list 9700 3470) (list 9690.0 3480) "")
(command "-LAYER" "S" "Textos" "")
(command "-COLOR" "7")
(command "-TEXT" "S" "Standard" "J" "C" (list 9670 3495) 10 0 "6xTV")
(command "-LAYER" "S" "APs" "")
(command "-COLOR" "3")
(command "_.PLINE" (list 9690.0 4400) (list 9710.0 4400) (list 9700 4425) (list 9690.0 4400) "")
(command "_.CIRCLE" (list 9700 4425) 10)
(command "_.CIRCLE" (list 9700 4425) 21.25)
(command "_.CIRCLE" (list 9700 4425) 30)
(command "-LAYER" "S" "Textos" "")
(command "-COLOR" "7")
(command "-TEXT" "S" "Standard" "J" "C" (list 9670 4415) 10 0 "4xAP")
(command "-LAYER" "S" "Telefonos" "")
(command "-COLOR" "4")
(command "_.PLINE" (list 9690.0 4480) (list 9710.0 4480) (list 9710.0 4510) (list 9690.0 4510) "C")
(command "_.CIRCLE" (list 9700 4517) 5)
(command "-LAYER" "S" "Textos" "")
(command "-COLOR" "7")
(command "-TEXT" "S" "Standard" "J" "C" (list 9670 4495) 10 0 "2xTEL")
(command "-LAYER" "S" "TVs" "")
(command "-COLOR" "5")
(command "_.PLINE" (list 9680.0 4560) (list 9720.0 4560) (list 9720.0 4585) (list 9680.0 4585) "C")
(command "_.PLINE" (list 9690.0 4560) (list 9710.0 4560) (list 9700 4550) (list 9690.0 4560) "")
(command "-LAYER" "S" "Textos" "")
(command "-COLOR" "7")
(command "-TEXT" "S" "Standard" "J" "C" (list 9670 4575) 10 0 "8xTV")
(command "-LAYER" "S" "APs" "")
(command "-COLOR" "3")
(command "_.PLINE" (list 9690.0 5400) (list 9710.0 5400) (list 9700 5425) (list 9690.0 5400) "")
(command "_.CIRCLE" (list 9700 5425) 10)
(command "_.CIRCLE" (list 9700 5425) 21.25)
(command "_.CIRCLE" (list 9700 5425) 30)
(command "-LAYER" "S" "Textos" "")
(command "-COLOR" "7")
(command "-TEXT" "S" "Standard" "J" "C" (list 9670 5415) 10 0 "6xAP")
(command "-LAYER" "S" "Telefonos" "")
(command "-COLOR" "4")
(command "_.PLINE" (list 9690.0 5480) (list 9710.0 5480) (list 9710.0 5510) (list 9690.0 5510) "C")
(command "_.CIRCLE" (list 9700 5517) 5)
(command "-LAYER" "S" "Textos" "")
(command "-COLOR" "7")
(command "-TEXT" "S" "Standard" "J" "C" (list 9670 5495) 10 0 "3xTEL")
(command "-LAYER" "S" "TVs" "")
(command "-COLOR" "5")
(command "_.PLINE" (list 9680.0 5560) (list 9720.0 5560) (list 9720.0 5585) (list 9680.0 5585) "C")
(command "_.PLINE" (list 9690.0 5560) (list 9710.0 5560) (list 9700 5550) (list 9690.0 5560) "")
(command "-LAYER" "S" "Textos" "")
(command "-COLOR" "7")
(command "-TEXT" "S" "Standard" "J" "C" (list 9670 5575) 10 0 "10xTV")
(command "-LAYER" "S" "APs" "")
(command "-COLOR" "3")
(command "_.PLINE" (list 9690.0 6560) (list 9710.0 6560) (list 9700 6585) (list 9690.0 6560) "")
(command "_.CIRCLE" (list 9700 6585) 10)
(command "_.CIRCLE" (list 9700 6585) 21.25)
(command "_.CIRCLE" (list 9700 6585) 30)
(command "-LAYER" "S" "Textos" "")
(command "-COLOR" "7")
(command "-TEXT" "S" "Standard" "J" "C" (list 9670 6575) 10 0 "6xAP")
(command "-LAYER" "S" "Telefonos" "")
(command "-COLOR" "4")
(command "_.PLINE" (list 9690.0 6640) (list 9710.0 6640) (list 9710.0 6670) (list 9690.0 6670) "C")
(command "_.CIRCLE" (list 9700 6677) 5)
(command "-LAYER" "S" "Textos" "")
(command "-COLOR" "7")
(command "-TEXT" "S" "Standard" "J" "C" (list 9670 6655) 10 0 "3xTEL")
(command "-LAYER" "S" "TVs" "")
(command "-COLOR" "5")
(command "_.PLINE" (list 9680.0 6720) (list 9720.0 6720) (list 9720.0 6745) (list 9680.0 6745) "C")
(command "_.PLINE" (list 9690.0 6720) (list 9710.0 6720) (list 9700 6710) (list 9690.0 6720) "")
(command "-LAYER" "S" "Textos" "")
(command "-COLOR" "7")
(command "-TEXT" "S" "Standard" "J" "C" (list 9670 6735) 10 0 "9xTV")
(command "-LAYER" "S" "APs" "")
(command "-COLOR" "3")
(command "_.PLINE" (list 9690.0 7800) (list 9710.0 7800) (list 9700 7825) (list 9690.0 7800) "")
(command "_.CIRCLE" (list 9700 7825) 10)
(command "_.CIRCLE" (list 9700 7825) 21.25)
(command "_.CIRCLE" (list 9700 7825) 30)
(command "-LAYER" "S" "Textos" "")
(command "-COLOR" "7")
(command "-TEXT" "S" "Standard" "J" "C" (list 9670 7815) 10 0 "4xAP")
(command "-LAYER" "S" "Telefonos" "")
(command "-COLOR" "4")
(command "_.PLINE" (list 9690.0 7880) (list 9710.0 7880) (list 9710.0 7910) (list 9690.0 7910) "C")
(command "_.CIRCLE" (list 9700 7917) 5)
(command "-LAYER" "S" "Textos" "")
(command "-COLOR" "7")
(command "-TEXT" "S" "Standard" "J" "C" (list 9670 7895) 10 0 "2xTEL")
(command "-LAYER" "S" "TVs" "")
(command "-COLOR" "5")
(command "_.PLINE" (list 9680.0 7960) (list 9720.0 7960) (list 9720.0 7985) (list 9680.0 7985) "C")
(command "_.PLINE" (list 9690.0 7960) (list 9710.0 7960) (list 9700 7950) (list 9690.0 7960) "")
(command "-LAYER" "S" "Textos" "")
(command "-COLOR" "7")
(command "-TEXT" "S" "Standard" "J" "C" (list 9670 7975) 10 0 "6xTV")

; === DIBUJAR TORRE: IDF10 ===
(command "-LAYER" "S" "Textos" "")
(command "-COLOR" "7")
(command "-TEXT" "S" "Standard" "J" "C" (list 10600 150) 25 0 "IDF10")
(command "-LAYER" "S" "Switches" "")
(command "-COLOR" "6")
(command "_.PLINE" (list 10650 150) (list 10800 150) (list 10800 190) (list 10650 190) "C")
(command "-LAYER" "S" "Textos" "")
(command "-COLOR" "7")
(command "-TEXT" "S" "Standard" "J" "MC" (list 10725.0 170.0) 8 0 "SW-CCTV (DS-3E3728F)")
(command "-LAYER" "S" "Switches" "")
(command "-COLOR" "6")
(command "_.PLINE" (list 10650 250) (list 10800 250) (list 10800 290) (list 10650 290) "C")
(command "-LAYER" "S" "Textos" "")
(command "-COLOR" "7")
(command "-TEXT" "S" "Standard" "J" "MC" (list 10725.0 270.0) 8 0 "SW-DATA (Meraki MS225)")
(command "-LAYER" "S" "Switches" "")
(command "-COLOR" "6")
(command "_.PLINE" (list 10650 350) (list 10800 350) (list 10800 390) (list 10650 390) "C")
(command "-LAYER" "S" "Textos" "")
(command "-COLOR" "7")
(command "-TEXT" "S" "Standard" "J" "MC" (list 10725.0 370.0) 8 0 "SW-IPTV (RG-NBS6002)")
(command "-LAYER" "S" "Switches" "")
(command "-COLOR" "6")
(command "_.PLINE" (list 10650 450) (list 10800 450) (list 10800 490) (list 10650 490) "C")
(command "-LAYER" "S" "Textos" "")
(command "-COLOR" "7")
(command "-TEXT" "S" "Standard" "J" "MC" (list 10725.0 470.0) 8 0 "SW-TEL (Meraki MS225)")
(command "-LAYER" "S" "Switches" "")
(command "-COLOR" "6")
(command "_.PLINE" (list 10650 550) (list 10800 550) (list 10800 590) (list 10650 590) "C")
(command "-LAYER" "S" "Textos" "")
(command "-COLOR" "7")
(command "-TEXT" "S" "Standard" "J" "MC" (list 10725.0 570.0) 8 0 "SW-WIFI (Meraki MS225)")
(command "-LAYER" "S" "APs" "")
(command "-COLOR" "3")
(command "_.PLINE" (list 10740.0 840) (list 10760.0 840) (list 10750 865) (list 10740.0 840) "")
(command "_.CIRCLE" (list 10750 865) 10)
(command "_.CIRCLE" (list 10750 865) 21.25)
(command "_.CIRCLE" (list 10750 865) 30)
(command "-LAYER" "S" "Textos" "")
(command "-COLOR" "7")
(command "-TEXT" "S" "Standard" "J" "C" (list 10720 855) 10 0 "6xAP")
(command "-LAYER" "S" "Telefonos" "")
(command "-COLOR" "4")
(command "_.PLINE" (list 10740.0 920) (list 10760.0 920) (list 10760.0 950) (list 10740.0 950) "C")
(command "_.CIRCLE" (list 10750 957) 5)
(command "-LAYER" "S" "Textos" "")
(command "-COLOR" "7")
(command "-TEXT" "S" "Standard" "J" "C" (list 10720 935) 10 0 "3xTEL")
(command "-LAYER" "S" "TVs" "")
(command "-COLOR" "5")
(command "_.PLINE" (list 10730.0 1000) (list 10770.0 1000) (list 10770.0 1025) (list 10730.0 1025) "C")
(command "_.PLINE" (list 10740.0 1000) (list 10760.0 1000) (list 10750 990) (list 10740.0 1000) "")
(command "-LAYER" "S" "Textos" "")
(command "-COLOR" "7")
(command "-TEXT" "S" "Standard" "J" "C" (list 10720 1015) 10 0 "11xTV")
(command "-LAYER" "S" "APs" "")
(command "-COLOR" "3")
(command "_.PLINE" (list 10740.0 2160) (list 10760.0 2160) (list 10750 2185) (list 10740.0 2160) "")
(command "_.CIRCLE" (list 10750 2185) 10)
(command "_.CIRCLE" (list 10750 2185) 21.25)
(command "_.CIRCLE" (list 10750 2185) 30)
(command "-LAYER" "S" "Textos" "")
(command "-COLOR" "7")
(command "-TEXT" "S" "Standard" "J" "C" (list 10720 2175) 10 0 "6xAP")
(command "-LAYER" "S" "Telefonos" "")
(command "-COLOR" "4")
(command "_.PLINE" (list 10740.0 2240) (list 10760.0 2240) (list 10760.0 2270) (list 10740.0 2270) "C")
(command "_.CIRCLE" (list 10750 2277) 5)
(command "-LAYER" "S" "Textos" "")
(command "-COLOR" "7")
(command "-TEXT" "S" "Standard" "J" "C" (list 10720 2255) 10 0 "2xTEL")
(command "-LAYER" "S" "TVs" "")
(command "-COLOR" "5")
(command "_.PLINE" (list 10730.0 2320) (list 10770.0 2320) (list 10770.0 2345) (list 10730.0 2345) "C")
(command "_.PLINE" (list 10740.0 2320) (list 10760.0 2320) (list 10750 2310) (list 10740.0 2320) "")
(command "-LAYER" "S" "Textos" "")
(command "-COLOR" "7")
(command "-TEXT" "S" "Standard" "J" "C" (list 10720 2335) 10 0 "10xTV")
(command "-LAYER" "S" "APs" "")
(command "-COLOR" "3")
(command "_.PLINE" (list 10740.0 4400) (list 10760.0 4400) (list 10750 4425) (list 10740.0 4400) "")
(command "_.CIRCLE" (list 10750 4425) 10)
(command "_.CIRCLE" (list 10750 4425) 21.25)
(command "_.CIRCLE" (list 10750 4425) 30)
(command "-LAYER" "S" "Textos" "")
(command "-COLOR" "7")
(command "-TEXT" "S" "Standard" "J" "C" (list 10720 4415) 10 0 "10xAP")
(command "-LAYER" "S" "Telefonos" "")
(command "-COLOR" "4")
(command "_.PLINE" (list 10740.0 4480) (list 10760.0 4480) (list 10760.0 4510) (list 10740.0 4510) "C")
(command "_.CIRCLE" (list 10750 4517) 5)
(command "-LAYER" "S" "Textos" "")
(command "-COLOR" "7")
(command "-TEXT" "S" "Standard" "J" "C" (list 10720 4495) 10 0 "5xTEL")
(command "-LAYER" "S" "TVs" "")
(command "-COLOR" "5")
(command "_.PLINE" (list 10730.0 4560) (list 10770.0 4560) (list 10770.0 4585) (list 10730.0 4585) "C")
(command "_.PLINE" (list 10740.0 4560) (list 10760.0 4560) (list 10750 4550) (list 10740.0 4560) "")
(command "-LAYER" "S" "Textos" "")
(command "-COLOR" "7")
(command "-TEXT" "S" "Standard" "J" "C" (list 10720 4575) 10 0 "15xTV")
(command "-LAYER" "S" "APs" "")
(command "-COLOR" "3")
(command "_.PLINE" (list 10740.0 5400) (list 10760.0 5400) (list 10750 5425) (list 10740.0 5400) "")
(command "_.CIRCLE" (list 10750 5425) 10)
(command "_.CIRCLE" (list 10750 5425) 21.25)
(command "_.CIRCLE" (list 10750 5425) 30)
(command "-LAYER" "S" "Textos" "")
(command "-COLOR" "7")
(command "-TEXT" "S" "Standard" "J" "C" (list 10720 5415) 10 0 "2xAP")
(command "-LAYER" "S" "Telefonos" "")
(command "-COLOR" "4")
(command "_.PLINE" (list 10740.0 5480) (list 10760.0 5480) (list 10760.0 5510) (list 10740.0 5510) "C")
(command "_.CIRCLE" (list 10750 5517) 5)
(command "-LAYER" "S" "Textos" "")
(command "-COLOR" "7")
(command "-TEXT" "S" "Standard" "J" "C" (list 10720 5495) 10 0 "1xTEL")
(command "-LAYER" "S" "TVs" "")
(command "-COLOR" "5")
(command "_.PLINE" (list 10730.0 5560) (list 10770.0 5560) (list 10770.0 5585) (list 10730.0 5585) "C")
(command "_.PLINE" (list 10740.0 5560) (list 10760.0 5560) (list 10750 5550) (list 10740.0 5560) "")
(command "-LAYER" "S" "Textos" "")
(command "-COLOR" "7")
(command "-TEXT" "S" "Standard" "J" "C" (list 10720 5575) 10 0 "3xTV")
(command "-LAYER" "S" "APs" "")
(command "-COLOR" "3")
(command "_.PLINE" (list 10740.0 6560) (list 10760.0 6560) (list 10750 6585) (list 10740.0 6560) "")
(command "_.CIRCLE" (list 10750 6585) 10)
(command "_.CIRCLE" (list 10750 6585) 21.25)
(command "_.CIRCLE" (list 10750 6585) 30)
(command "-LAYER" "S" "Textos" "")
(command "-COLOR" "7")
(command "-TEXT" "S" "Standard" "J" "C" (list 10720 6575) 10 0 "6xAP")
(command "-LAYER" "S" "Telefonos" "")
(command "-COLOR" "4")
(command "_.PLINE" (list 10740.0 6640) (list 10760.0 6640) (list 10760.0 6670) (list 10740.0 6670) "C")
(command "_.CIRCLE" (list 10750 6677) 5)
(command "-LAYER" "S" "Textos" "")
(command "-COLOR" "7")
(command "-TEXT" "S" "Standard" "J" "C" (list 10720 6655) 10 0 "3xTEL")
(command "-LAYER" "S" "TVs" "")
(command "-COLOR" "5")
(command "_.PLINE" (list 10730.0 6720) (list 10770.0 6720) (list 10770.0 6745) (list 10730.0 6745) "C")
(command "_.PLINE" (list 10740.0 6720) (list 10760.0 6720) (list 10750 6710) (list 10740.0 6720) "")
(command "-LAYER" "S" "Textos" "")
(command "-COLOR" "7")
(command "-TEXT" "S" "Standard" "J" "C" (list 10720 6735) 10 0 "10xTV")
(command "-LAYER" "S" "APs" "")
(command "-COLOR" "3")
(command "_.PLINE" (list 10740.0 7800) (list 10760.0 7800) (list 10750 7825) (list 10740.0 7800) "")
(command "_.CIRCLE" (list 10750 7825) 10)
(command "_.CIRCLE" (list 10750 7825) 21.25)
(command "_.CIRCLE" (list 10750 7825) 30)
(command "-LAYER" "S" "Textos" "")
(command "-COLOR" "7")
(command "-TEXT" "S" "Standard" "J" "C" (list 10720 7815) 10 0 "2xAP")
(command "-LAYER" "S" "Telefonos" "")
(command "-COLOR" "4")
(command "_.PLINE" (list 10740.0 7880) (list 10760.0 7880) (list 10760.0 7910) (list 10740.0 7910) "C")
(command "_.CIRCLE" (list 10750 7917) 5)
(command "-LAYER" "S" "Textos" "")
(command "-COLOR" "7")
(command "-TEXT" "S" "Standard" "J" "C" (list 10720 7895) 10 0 "1xTEL")
(command "-LAYER" "S" "TVs" "")
(command "-COLOR" "5")
(command "_.PLINE" (list 10730.0 7960) (list 10770.0 7960) (list 10770.0 7985) (list 10730.0 7985) "C")
(command "_.PLINE" (list 10740.0 7960) (list 10760.0 7960) (list 10750 7950) (list 10740.0 7960) "")
(command "-LAYER" "S" "Textos" "")
(command "-COLOR" "7")
(command "-TEXT" "S" "Standard" "J" "C" (list 10720 7975) 10 0 "4xTV")

; === DIBUJAR TORRE: IDF11 ===
(command "-LAYER" "S" "Textos" "")
(command "-COLOR" "7")
(command "-TEXT" "S" "Standard" "J" "C" (list 11650 150) 25 0 "IDF11")
(command "-LAYER" "S" "Switches" "")
(command "-COLOR" "6")
(command "_.PLINE" (list 11700 150) (list 11850 150) (list 11850 190) (list 11700 190) "C")
(command "-LAYER" "S" "Textos" "")
(command "-COLOR" "7")
(command "-TEXT" "S" "Standard" "J" "MC" (list 11775.0 170.0) 8 0 "SW-CCTV (DS-3E3728F)")
(command "-LAYER" "S" "Switches" "")
(command "-COLOR" "6")
(command "_.PLINE" (list 11700 250) (list 11850 250) (list 11850 290) (list 11700 290) "C")
(command "-LAYER" "S" "Textos" "")
(command "-COLOR" "7")
(command "-TEXT" "S" "Standard" "J" "MC" (list 11775.0 270.0) 8 0 "SW-DATA (Meraki MS225)")
(command "-LAYER" "S" "Switches" "")
(command "-COLOR" "6")
(command "_.PLINE" (list 11700 350) (list 11850 350) (list 11850 390) (list 11700 390) "C")
(command "-LAYER" "S" "Textos" "")
(command "-COLOR" "7")
(command "-TEXT" "S" "Standard" "J" "MC" (list 11775.0 370.0) 8 0 "SW-IPTV (RG-NBS6002)")
(command "-LAYER" "S" "Switches" "")
(command "-COLOR" "6")
(command "_.PLINE" (list 11700 450) (list 11850 450) (list 11850 490) (list 11700 490) "C")
(command "-LAYER" "S" "Textos" "")
(command "-COLOR" "7")
(command "-TEXT" "S" "Standard" "J" "MC" (list 11775.0 470.0) 8 0 "SW-TEL (Meraki MS225)")
(command "-LAYER" "S" "Switches" "")
(command "-COLOR" "6")
(command "_.PLINE" (list 11700 550) (list 11850 550) (list 11850 590) (list 11700 590) "C")
(command "-LAYER" "S" "Textos" "")
(command "-COLOR" "7")
(command "-TEXT" "S" "Standard" "J" "MC" (list 11775.0 570.0) 8 0 "SW-WIFI (Meraki MS225)")
(command "-LAYER" "S" "APs" "")
(command "-COLOR" "3")
(command "_.PLINE" (list 11790.0 840) (list 11810.0 840) (list 11800 865) (list 11790.0 840) "")
(command "_.CIRCLE" (list 11800 865) 10)
(command "_.CIRCLE" (list 11800 865) 21.25)
(command "_.CIRCLE" (list 11800 865) 30)
(command "-LAYER" "S" "Textos" "")
(command "-COLOR" "7")
(command "-TEXT" "S" "Standard" "J" "C" (list 11770 855) 10 0 "2xAP")
(command "-LAYER" "S" "Telefonos" "")
(command "-COLOR" "4")
(command "_.PLINE" (list 11790.0 920) (list 11810.0 920) (list 11810.0 950) (list 11790.0 950) "C")
(command "_.CIRCLE" (list 11800 957) 5)
(command "-LAYER" "S" "Textos" "")
(command "-COLOR" "7")
(command "-TEXT" "S" "Standard" "J" "C" (list 11770 935) 10 0 "1xTEL")
(command "-LAYER" "S" "TVs" "")
(command "-COLOR" "5")
(command "_.PLINE" (list 11780.0 1000) (list 11820.0 1000) (list 11820.0 1025) (list 11780.0 1025) "C")
(command "_.PLINE" (list 11790.0 1000) (list 11810.0 1000) (list 11800 990) (list 11790.0 1000) "")
(command "-LAYER" "S" "Textos" "")
(command "-COLOR" "7")
(command "-TEXT" "S" "Standard" "J" "C" (list 11770 1015) 10 0 "3xTV")
(command "-LAYER" "S" "APs" "")
(command "-COLOR" "3")
(command "_.PLINE" (list 11790.0 2160) (list 11810.0 2160) (list 11800 2185) (list 11790.0 2160) "")
(command "_.CIRCLE" (list 11800 2185) 10)
(command "_.CIRCLE" (list 11800 2185) 21.25)
(command "_.CIRCLE" (list 11800 2185) 30)
(command "-LAYER" "S" "Textos" "")
(command "-COLOR" "7")
(command "-TEXT" "S" "Standard" "J" "C" (list 11770 2175) 10 0 "2xAP")
(command "-LAYER" "S" "Telefonos" "")
(command "-COLOR" "4")
(command "_.PLINE" (list 11790.0 2240) (list 11810.0 2240) (list 11810.0 2270) (list 11790.0 2270) "C")
(command "_.CIRCLE" (list 11800 2277) 5)
(command "-LAYER" "S" "Textos" "")
(command "-COLOR" "7")
(command "-TEXT" "S" "Standard" "J" "C" (list 11770 2255) 10 0 "1xTEL")
(command "-LAYER" "S" "TVs" "")
(command "-COLOR" "5")
(command "_.PLINE" (list 11780.0 2320) (list 11820.0 2320) (list 11820.0 2345) (list 11780.0 2345) "C")
(command "_.PLINE" (list 11790.0 2320) (list 11810.0 2320) (list 11800 2310) (list 11790.0 2320) "")
(command "-LAYER" "S" "Textos" "")
(command "-COLOR" "7")
(command "-TEXT" "S" "Standard" "J" "C" (list 11770 2335) 10 0 "2xTV")
(command "-LAYER" "S" "APs" "")
(command "-COLOR" "3")
(command "_.PLINE" (list 11790.0 3320) (list 11810.0 3320) (list 11800 3345) (list 11790.0 3320) "")
(command "_.CIRCLE" (list 11800 3345) 10)
(command "_.CIRCLE" (list 11800 3345) 21.25)
(command "_.CIRCLE" (list 11800 3345) 30)
(command "-LAYER" "S" "Textos" "")
(command "-COLOR" "7")
(command "-TEXT" "S" "Standard" "J" "C" (list 11770 3335) 10 0 "7xAP")
(command "-LAYER" "S" "Telefonos" "")
(command "-COLOR" "4")
(command "_.PLINE" (list 11790.0 3400) (list 11810.0 3400) (list 11810.0 3430) (list 11790.0 3430) "C")
(command "_.CIRCLE" (list 11800 3437) 5)
(command "-LAYER" "S" "Textos" "")
(command "-COLOR" "7")
(command "-TEXT" "S" "Standard" "J" "C" (list 11770 3415) 10 0 "3xTEL")
(command "-LAYER" "S" "TVs" "")
(command "-COLOR" "5")
(command "_.PLINE" (list 11780.0 3480) (list 11820.0 3480) (list 11820.0 3505) (list 11780.0 3505) "C")
(command "_.PLINE" (list 11790.0 3480) (list 11810.0 3480) (list 11800 3470) (list 11790.0 3480) "")
(command "-LAYER" "S" "Textos" "")
(command "-COLOR" "7")
(command "-TEXT" "S" "Standard" "J" "C" (list 11770 3495) 10 0 "12xTV")
(command "-LAYER" "S" "APs" "")
(command "-COLOR" "3")
(command "_.PLINE" (list 11790.0 6560) (list 11810.0 6560) (list 11800 6585) (list 11790.0 6560) "")
(command "_.CIRCLE" (list 11800 6585) 10)
(command "_.CIRCLE" (list 11800 6585) 21.25)
(command "_.CIRCLE" (list 11800 6585) 30)
(command "-LAYER" "S" "Textos" "")
(command "-COLOR" "7")
(command "-TEXT" "S" "Standard" "J" "C" (list 11770 6575) 10 0 "2xAP")
(command "-LAYER" "S" "Telefonos" "")
(command "-COLOR" "4")
(command "_.PLINE" (list 11790.0 6640) (list 11810.0 6640) (list 11810.0 6670) (list 11790.0 6670) "C")
(command "_.CIRCLE" (list 11800 6677) 5)
(command "-LAYER" "S" "Textos" "")
(command "-COLOR" "7")
(command "-TEXT" "S" "Standard" "J" "C" (list 11770 6655) 10 0 "1xTEL")
(command "-LAYER" "S" "TVs" "")
(command "-COLOR" "5")
(command "_.PLINE" (list 11780.0 6720) (list 11820.0 6720) (list 11820.0 6745) (list 11780.0 6745) "C")
(command "_.PLINE" (list 11790.0 6720) (list 11810.0 6720) (list 11800 6710) (list 11790.0 6720) "")
(command "-LAYER" "S" "Textos" "")
(command "-COLOR" "7")
(command "-TEXT" "S" "Standard" "J" "C" (list 11770 6735) 10 0 "3xTV")
(command "-LAYER" "S" "APs" "")
(command "-COLOR" "3")
(command "_.PLINE" (list 11790.0 7800) (list 11810.0 7800) (list 11800 7825) (list 11790.0 7800) "")
(command "_.CIRCLE" (list 11800 7825) 10)
(command "_.CIRCLE" (list 11800 7825) 21.25)
(command "_.CIRCLE" (list 11800 7825) 30)
(command "-LAYER" "S" "Textos" "")
(command "-COLOR" "7")
(command "-TEXT" "S" "Standard" "J" "C" (list 11770 7815) 10 0 "4xAP")
(command "-LAYER" "S" "Telefonos" "")
(command "-COLOR" "4")
(command "_.PLINE" (list 11790.0 7880) (list 11810.0 7880) (list 11810.0 7910) (list 11790.0 7910) "C")
(command "_.CIRCLE" (list 11800 7917) 5)
(command "-LAYER" "S" "Textos" "")
(command "-COLOR" "7")
(command "-TEXT" "S" "Standard" "J" "C" (list 11770 7895) 10 0 "2xTEL")
(command "-LAYER" "S" "TVs" "")
(command "-COLOR" "5")
(command "_.PLINE" (list 11780.0 7960) (list 11820.0 7960) (list 11820.0 7985) (list 11780.0 7985) "C")
(command "_.PLINE" (list 11790.0 7960) (list 11810.0 7960) (list 11800 7950) (list 11790.0 7960) "")
(command "-LAYER" "S" "Textos" "")
(command "-COLOR" "7")
(command "-TEXT" "S" "Standard" "J" "C" (list 11770 7975) 10 0 "7xTV")

; === DIBUJAR TORRE: IDF12 ===
(command "-LAYER" "S" "Textos" "")
(command "-COLOR" "7")
(command "-TEXT" "S" "Standard" "J" "C" (list 12700 150) 25 0 "IDF12")
(command "-LAYER" "S" "Switches" "")
(command "-COLOR" "6")
(command "_.PLINE" (list 12750 150) (list 12900 150) (list 12900 190) (list 12750 190) "C")
(command "-LAYER" "S" "Textos" "")
(command "-COLOR" "7")
(command "-TEXT" "S" "Standard" "J" "MC" (list 12825.0 170.0) 8 0 "SW-CCTV (DS-3E3728F)")
(command "-LAYER" "S" "Switches" "")
(command "-COLOR" "6")
(command "_.PLINE" (list 12750 250) (list 12900 250) (list 12900 290) (list 12750 290) "C")
(command "-LAYER" "S" "Textos" "")
(command "-COLOR" "7")
(command "-TEXT" "S" "Standard" "J" "MC" (list 12825.0 270.0) 8 0 "SW-DATA (Meraki MS225)")
(command "-LAYER" "S" "Switches" "")
(command "-COLOR" "6")
(command "_.PLINE" (list 12750 350) (list 12900 350) (list 12900 390) (list 12750 390) "C")
(command "-LAYER" "S" "Textos" "")
(command "-COLOR" "7")
(command "-TEXT" "S" "Standard" "J" "MC" (list 12825.0 370.0) 8 0 "SW-IPTV (RG-NBS6002)")
(command "-LAYER" "S" "Switches" "")
(command "-COLOR" "6")
(command "_.PLINE" (list 12750 450) (list 12900 450) (list 12900 490) (list 12750 490) "C")
(command "-LAYER" "S" "Textos" "")
(command "-COLOR" "7")
(command "-TEXT" "S" "Standard" "J" "MC" (list 12825.0 470.0) 8 0 "SW-TEL (Meraki MS225)")
(command "-LAYER" "S" "Switches" "")
(command "-COLOR" "6")
(command "_.PLINE" (list 12750 550) (list 12900 550) (list 12900 590) (list 12750 590) "C")
(command "-LAYER" "S" "Textos" "")
(command "-COLOR" "7")
(command "-TEXT" "S" "Standard" "J" "MC" (list 12825.0 570.0) 8 0 "SW-WIFI (Meraki MS225)")
(command "-LAYER" "S" "APs" "")
(command "-COLOR" "3")
(command "_.PLINE" (list 12840.0 840) (list 12860.0 840) (list 12850 865) (list 12840.0 840) "")
(command "_.CIRCLE" (list 12850 865) 10)
(command "_.CIRCLE" (list 12850 865) 21.25)
(command "_.CIRCLE" (list 12850 865) 30)
(command "-LAYER" "S" "Textos" "")
(command "-COLOR" "7")
(command "-TEXT" "S" "Standard" "J" "C" (list 12820 855) 10 0 "4xAP")
(command "-LAYER" "S" "Telefonos" "")
(command "-COLOR" "4")
(command "_.PLINE" (list 12840.0 920) (list 12860.0 920) (list 12860.0 950) (list 12840.0 950) "C")
(command "_.CIRCLE" (list 12850 957) 5)
(command "-LAYER" "S" "Textos" "")
(command "-COLOR" "7")
(command "-TEXT" "S" "Standard" "J" "C" (list 12820 935) 10 0 "2xTEL")
(command "-LAYER" "S" "TVs" "")
(command "-COLOR" "5")
(command "_.PLINE" (list 12830.0 1000) (list 12870.0 1000) (list 12870.0 1025) (list 12830.0 1025) "C")
(command "_.PLINE" (list 12840.0 1000) (list 12860.0 1000) (list 12850 990) (list 12840.0 1000) "")
(command "-LAYER" "S" "Textos" "")
(command "-COLOR" "7")
(command "-TEXT" "S" "Standard" "J" "C" (list 12820 1015) 10 0 "8xTV")
(command "-LAYER" "S" "APs" "")
(command "-COLOR" "3")
(command "_.PLINE" (list 12840.0 2160) (list 12860.0 2160) (list 12850 2185) (list 12840.0 2160) "")
(command "_.CIRCLE" (list 12850 2185) 10)
(command "_.CIRCLE" (list 12850 2185) 21.25)
(command "_.CIRCLE" (list 12850 2185) 30)
(command "-LAYER" "S" "Textos" "")
(command "-COLOR" "7")
(command "-TEXT" "S" "Standard" "J" "C" (list 12820 2175) 10 0 "8xAP")
(command "-LAYER" "S" "Telefonos" "")
(command "-COLOR" "4")
(command "_.PLINE" (list 12840.0 2240) (list 12860.0 2240) (list 12860.0 2270) (list 12840.0 2270) "C")
(command "_.CIRCLE" (list 12850 2277) 5)
(command "-LAYER" "S" "Textos" "")
(command "-COLOR" "7")
(command "-TEXT" "S" "Standard" "J" "C" (list 12820 2255) 10 0 "3xTEL")
(command "-LAYER" "S" "TVs" "")
(command "-COLOR" "5")
(command "_.PLINE" (list 12830.0 2320) (list 12870.0 2320) (list 12870.0 2345) (list 12830.0 2345) "C")
(command "_.PLINE" (list 12840.0 2320) (list 12860.0 2320) (list 12850 2310) (list 12840.0 2320) "")
(command "-LAYER" "S" "Textos" "")
(command "-COLOR" "7")
(command "-TEXT" "S" "Standard" "J" "C" (list 12820 2335) 10 0 "13xTV")

; === DIBUJAR TORRE: IDF13 ===
(command "-LAYER" "S" "Textos" "")
(command "-COLOR" "7")
(command "-TEXT" "S" "Standard" "J" "C" (list 13750 150) 25 0 "IDF13")
(command "-LAYER" "S" "Switches" "")
(command "-COLOR" "6")
(command "_.PLINE" (list 13800 150) (list 13950 150) (list 13950 190) (list 13800 190) "C")
(command "-LAYER" "S" "Textos" "")
(command "-COLOR" "7")
(command "-TEXT" "S" "Standard" "J" "MC" (list 13875.0 170.0) 8 0 "SW-CCTV (DS-3E3728F)")
(command "-LAYER" "S" "Switches" "")
(command "-COLOR" "6")
(command "_.PLINE" (list 13800 250) (list 13950 250) (list 13950 290) (list 13800 290) "C")
(command "-LAYER" "S" "Textos" "")
(command "-COLOR" "7")
(command "-TEXT" "S" "Standard" "J" "MC" (list 13875.0 270.0) 8 0 "SW-DATA (Meraki MS225)")
(command "-LAYER" "S" "Switches" "")
(command "-COLOR" "6")
(command "_.PLINE" (list 13800 350) (list 13950 350) (list 13950 390) (list 13800 390) "C")
(command "-LAYER" "S" "Textos" "")
(command "-COLOR" "7")
(command "-TEXT" "S" "Standard" "J" "MC" (list 13875.0 370.0) 8 0 "SW-IPTV (RG-NBS6002)")
(command "-LAYER" "S" "Switches" "")
(command "-COLOR" "6")
(command "_.PLINE" (list 13800 450) (list 13950 450) (list 13950 490) (list 13800 490) "C")
(command "-LAYER" "S" "Textos" "")
(command "-COLOR" "7")
(command "-TEXT" "S" "Standard" "J" "MC" (list 13875.0 470.0) 8 0 "SW-TEL (Meraki MS225)")
(command "-LAYER" "S" "Switches" "")
(command "-COLOR" "6")
(command "_.PLINE" (list 13800 550) (list 13950 550) (list 13950 590) (list 13800 590) "C")
(command "-LAYER" "S" "Textos" "")
(command "-COLOR" "7")
(command "-TEXT" "S" "Standard" "J" "MC" (list 13875.0 570.0) 8 0 "SW-WIFI (Meraki MS225)")
(command "-LAYER" "S" "APs" "")
(command "-COLOR" "3")
(command "_.PLINE" (list 13890.0 840) (list 13910.0 840) (list 13900 865) (list 13890.0 840) "")
(command "_.CIRCLE" (list 13900 865) 10)
(command "_.CIRCLE" (list 13900 865) 21.25)
(command "_.CIRCLE" (list 13900 865) 30)
(command "-LAYER" "S" "Textos" "")
(command "-COLOR" "7")
(command "-TEXT" "S" "Standard" "J" "C" (list 13870 855) 10 0 "7xAP")
(command "-LAYER" "S" "Telefonos" "")
(command "-COLOR" "4")
(command "_.PLINE" (list 13890.0 920) (list 13910.0 920) (list 13910.0 950) (list 13890.0 950) "C")
(command "_.CIRCLE" (list 13900 957) 5)
(command "-LAYER" "S" "Textos" "")
(command "-COLOR" "7")
(command "-TEXT" "S" "Standard" "J" "C" (list 13870 935) 10 0 "3xTEL")
(command "-LAYER" "S" "TVs" "")
(command "-COLOR" "5")
(command "_.PLINE" (list 13880.0 1000) (list 13920.0 1000) (list 13920.0 1025) (list 13880.0 1025) "C")
(command "_.PLINE" (list 13890.0 1000) (list 13910.0 1000) (list 13900 990) (list 13890.0 1000) "")
(command "-LAYER" "S" "Textos" "")
(command "-COLOR" "7")
(command "-TEXT" "S" "Standard" "J" "C" (list 13870 1015) 10 0 "12xTV")
(command "-LAYER" "S" "APs" "")
(command "-COLOR" "3")
(command "_.PLINE" (list 13890.0 2160) (list 13910.0 2160) (list 13900 2185) (list 13890.0 2160) "")
(command "_.CIRCLE" (list 13900 2185) 10)
(command "_.CIRCLE" (list 13900 2185) 21.25)
(command "_.CIRCLE" (list 13900 2185) 30)
(command "-LAYER" "S" "Textos" "")
(command "-COLOR" "7")
(command "-TEXT" "S" "Standard" "J" "C" (list 13870 2175) 10 0 "8xAP")
(command "-LAYER" "S" "Telefonos" "")
(command "-COLOR" "4")
(command "_.PLINE" (list 13890.0 2240) (list 13910.0 2240) (list 13910.0 2270) (list 13890.0 2270) "C")
(command "_.CIRCLE" (list 13900 2277) 5)
(command "-LAYER" "S" "Textos" "")
(command "-COLOR" "7")
(command "-TEXT" "S" "Standard" "J" "C" (list 13870 2255) 10 0 "4xTEL")
(command "-LAYER" "S" "TVs" "")
(command "-COLOR" "5")
(command "_.PLINE" (list 13880.0 2320) (list 13920.0 2320) (list 13920.0 2345) (list 13880.0 2345) "C")
(command "_.PLINE" (list 13890.0 2320) (list 13910.0 2320) (list 13900 2310) (list 13890.0 2320) "")
(command "-LAYER" "S" "Textos" "")
(command "-COLOR" "7")
(command "-TEXT" "S" "Standard" "J" "C" (list 13870 2335) 10 0 "14xTV")
(command "-LAYER" "S" "APs" "")
(command "-COLOR" "3")
(command "_.PLINE" (list 13890.0 3320) (list 13910.0 3320) (list 13900 3345) (list 13890.0 3320) "")
(command "_.CIRCLE" (list 13900 3345) 10)
(command "_.CIRCLE" (list 13900 3345) 21.25)
(command "_.CIRCLE" (list 13900 3345) 30)
(command "-LAYER" "S" "Textos" "")
(command "-COLOR" "7")
(command "-TEXT" "S" "Standard" "J" "C" (list 13870 3335) 10 0 "2xAP")
(command "-LAYER" "S" "Telefonos" "")
(command "-COLOR" "4")
(command "_.PLINE" (list 13890.0 3400) (list 13910.0 3400) (list 13910.0 3430) (list 13890.0 3430) "C")
(command "_.CIRCLE" (list 13900 3437) 5)
(command "-LAYER" "S" "Textos" "")
(command "-COLOR" "7")
(command "-TEXT" "S" "Standard" "J" "C" (list 13870 3415) 10 0 "1xTEL")
(command "-LAYER" "S" "TVs" "")
(command "-COLOR" "5")
(command "_.PLINE" (list 13880.0 3480) (list 13920.0 3480) (list 13920.0 3505) (list 13880.0 3505) "C")
(command "_.PLINE" (list 13890.0 3480) (list 13910.0 3480) (list 13900 3470) (list 13890.0 3480) "")
(command "-LAYER" "S" "Textos" "")
(command "-COLOR" "7")
(command "-TEXT" "S" "Standard" "J" "C" (list 13870 3495) 10 0 "4xTV")
(command "-LAYER" "S" "APs" "")
(command "-COLOR" "3")
(command "_.PLINE" (list 13890.0 4400) (list 13910.0 4400) (list 13900 4425) (list 13890.0 4400) "")
(command "_.CIRCLE" (list 13900 4425) 10)
(command "_.CIRCLE" (list 13900 4425) 21.25)
(command "_.CIRCLE" (list 13900 4425) 30)
(command "-LAYER" "S" "Textos" "")
(command "-COLOR" "7")
(command "-TEXT" "S" "Standard" "J" "C" (list 13870 4415) 10 0 "4xAP")
(command "-LAYER" "S" "Telefonos" "")
(command "-COLOR" "4")
(command "_.PLINE" (list 13890.0 4480) (list 13910.0 4480) (list 13910.0 4510) (list 13890.0 4510) "C")
(command "_.CIRCLE" (list 13900 4517) 5)
(command "-LAYER" "S" "Textos" "")
(command "-COLOR" "7")
(command "-TEXT" "S" "Standard" "J" "C" (list 13870 4495) 10 0 "2xTEL")
(command "-LAYER" "S" "TVs" "")
(command "-COLOR" "5")
(command "_.PLINE" (list 13880.0 4560) (list 13920.0 4560) (list 13920.0 4585) (list 13880.0 4585) "C")
(command "_.PLINE" (list 13890.0 4560) (list 13910.0 4560) (list 13900 4550) (list 13890.0 4560) "")
(command "-LAYER" "S" "Textos" "")
(command "-COLOR" "7")
(command "-TEXT" "S" "Standard" "J" "C" (list 13870 4575) 10 0 "6xTV")
(command "-LAYER" "S" "APs" "")
(command "-COLOR" "3")
(command "_.PLINE" (list 13890.0 6560) (list 13910.0 6560) (list 13900 6585) (list 13890.0 6560) "")
(command "_.CIRCLE" (list 13900 6585) 10)
(command "_.CIRCLE" (list 13900 6585) 21.25)
(command "_.CIRCLE" (list 13900 6585) 30)
(command "-LAYER" "S" "Textos" "")
(command "-COLOR" "7")
(command "-TEXT" "S" "Standard" "J" "C" (list 13870 6575) 10 0 "4xAP")
(command "-LAYER" "S" "Telefonos" "")
(command "-COLOR" "4")
(command "_.PLINE" (list 13890.0 6640) (list 13910.0 6640) (list 13910.0 6670) (list 13890.0 6670) "C")
(command "_.CIRCLE" (list 13900 6677) 5)
(command "-LAYER" "S" "Textos" "")
(command "-COLOR" "7")
(command "-TEXT" "S" "Standard" "J" "C" (list 13870 6655) 10 0 "2xTEL")
(command "-LAYER" "S" "TVs" "")
(command "-COLOR" "5")
(command "_.PLINE" (list 13880.0 6720) (list 13920.0 6720) (list 13920.0 6745) (list 13880.0 6745) "C")
(command "_.PLINE" (list 13890.0 6720) (list 13910.0 6720) (list 13900 6710) (list 13890.0 6720) "")
(command "-LAYER" "S" "Textos" "")
(command "-COLOR" "7")
(command "-TEXT" "S" "Standard" "J" "C" (list 13870 6735) 10 0 "6xTV")
(command "-LAYER" "S" "APs" "")
(command "-COLOR" "3")
(command "_.PLINE" (list 13890.0 7800) (list 13910.0 7800) (list 13900 7825) (list 13890.0 7800) "")
(command "_.CIRCLE" (list 13900 7825) 10)
(command "_.CIRCLE" (list 13900 7825) 21.25)
(command "_.CIRCLE" (list 13900 7825) 30)
(command "-LAYER" "S" "Textos" "")
(command "-COLOR" "7")
(command "-TEXT" "S" "Standard" "J" "C" (list 13870 7815) 10 0 "7xAP")
(command "-LAYER" "S" "Telefonos" "")
(command "-COLOR" "4")
(command "_.PLINE" (list 13890.0 7880) (list 13910.0 7880) (list 13910.0 7910) (list 13890.0 7910) "C")
(command "_.CIRCLE" (list 13900 7917) 5)
(command "-LAYER" "S" "Textos" "")
(command "-COLOR" "7")
(command "-TEXT" "S" "Standard" "J" "C" (list 13870 7895) 10 0 "3xTEL")
(command "-LAYER" "S" "TVs" "")
(command "-COLOR" "5")
(command "_.PLINE" (list 13880.0 7960) (list 13920.0 7960) (list 13920.0 7985) (list 13880.0 7985) "C")
(command "_.PLINE" (list 13890.0 7960) (list 13910.0 7960) (list 13900 7950) (list 13890.0 7960) "")
(command "-LAYER" "S" "Textos" "")
(command "-COLOR" "7")
(command "-TEXT" "S" "Standard" "J" "C" (list 13870 7975) 10 0 "11xTV")

; === DIBUJAR TORRE: IDF14 ===
(command "-LAYER" "S" "Textos" "")
(command "-COLOR" "7")
(command "-TEXT" "S" "Standard" "J" "C" (list 14800 150) 25 0 "IDF14")
(command "-LAYER" "S" "Switches" "")
(command "-COLOR" "6")
(command "_.PLINE" (list 14850 150) (list 15000 150) (list 15000 190) (list 14850 190) "C")
(command "-LAYER" "S" "Textos" "")
(command "-COLOR" "7")
(command "-TEXT" "S" "Standard" "J" "MC" (list 14925.0 170.0) 8 0 "SW-CCTV (DS-3E3728F)")
(command "-LAYER" "S" "Switches" "")
(command "-COLOR" "6")
(command "_.PLINE" (list 14850 250) (list 15000 250) (list 15000 290) (list 14850 290) "C")
(command "-LAYER" "S" "Textos" "")
(command "-COLOR" "7")
(command "-TEXT" "S" "Standard" "J" "MC" (list 14925.0 270.0) 8 0 "SW-DATA (Meraki MS225)")
(command "-LAYER" "S" "Switches" "")
(command "-COLOR" "6")
(command "_.PLINE" (list 14850 350) (list 15000 350) (list 15000 390) (list 14850 390) "C")
(command "-LAYER" "S" "Textos" "")
(command "-COLOR" "7")
(command "-TEXT" "S" "Standard" "J" "MC" (list 14925.0 370.0) 8 0 "SW-IPTV (RG-NBS6002)")
(command "-LAYER" "S" "Switches" "")
(command "-COLOR" "6")
(command "_.PLINE" (list 14850 450) (list 15000 450) (list 15000 490) (list 14850 490) "C")
(command "-LAYER" "S" "Textos" "")
(command "-COLOR" "7")
(command "-TEXT" "S" "Standard" "J" "MC" (list 14925.0 470.0) 8 0 "SW-TEL (Meraki MS225)")
(command "-LAYER" "S" "Switches" "")
(command "-COLOR" "6")
(command "_.PLINE" (list 14850 550) (list 15000 550) (list 15000 590) (list 14850 590) "C")
(command "-LAYER" "S" "Textos" "")
(command "-COLOR" "7")
(command "-TEXT" "S" "Standard" "J" "MC" (list 14925.0 570.0) 8 0 "SW-WIFI (Meraki MS225)")
(command "-LAYER" "S" "APs" "")
(command "-COLOR" "3")
(command "_.PLINE" (list 14940.0 840) (list 14960.0 840) (list 14950 865) (list 14940.0 840) "")
(command "_.CIRCLE" (list 14950 865) 10)
(command "_.CIRCLE" (list 14950 865) 21.25)
(command "_.CIRCLE" (list 14950 865) 30)
(command "-LAYER" "S" "Textos" "")
(command "-COLOR" "7")
(command "-TEXT" "S" "Standard" "J" "C" (list 14920 855) 10 0 "4xAP")
(command "-LAYER" "S" "Telefonos" "")
(command "-COLOR" "4")
(command "_.PLINE" (list 14940.0 920) (list 14960.0 920) (list 14960.0 950) (list 14940.0 950) "C")
(command "_.CIRCLE" (list 14950 957) 5)
(command "-LAYER" "S" "Textos" "")
(command "-COLOR" "7")
(command "-TEXT" "S" "Standard" "J" "C" (list 14920 935) 10 0 "2xTEL")
(command "-LAYER" "S" "TVs" "")
(command "-COLOR" "5")
(command "_.PLINE" (list 14930.0 1000) (list 14970.0 1000) (list 14970.0 1025) (list 14930.0 1025) "C")
(command "_.PLINE" (list 14940.0 1000) (list 14960.0 1000) (list 14950 990) (list 14940.0 1000) "")
(command "-LAYER" "S" "Textos" "")
(command "-COLOR" "7")
(command "-TEXT" "S" "Standard" "J" "C" (list 14920 1015) 10 0 "6xTV")
(command "-LAYER" "S" "APs" "")
(command "-COLOR" "3")
(command "_.PLINE" (list 14940.0 2160) (list 14960.0 2160) (list 14950 2185) (list 14940.0 2160) "")
(command "_.CIRCLE" (list 14950 2185) 10)
(command "_.CIRCLE" (list 14950 2185) 21.25)
(command "_.CIRCLE" (list 14950 2185) 30)
(command "-LAYER" "S" "Textos" "")
(command "-COLOR" "7")
(command "-TEXT" "S" "Standard" "J" "C" (list 14920 2175) 10 0 "9xAP")
(command "-LAYER" "S" "Telefonos" "")
(command "-COLOR" "4")
(command "_.PLINE" (list 14940.0 2240) (list 14960.0 2240) (list 14960.0 2270) (list 14940.0 2270) "C")
(command "_.CIRCLE" (list 14950 2277) 5)
(command "-LAYER" "S" "Textos" "")
(command "-COLOR" "7")
(command "-TEXT" "S" "Standard" "J" "C" (list 14920 2255) 10 0 "4xTEL")
(command "-LAYER" "S" "TVs" "")
(command "-COLOR" "5")
(command "_.PLINE" (list 14930.0 2320) (list 14970.0 2320) (list 14970.0 2345) (list 14930.0 2345) "C")
(command "_.PLINE" (list 14940.0 2320) (list 14960.0 2320) (list 14950 2310) (list 14940.0 2320) "")
(command "-LAYER" "S" "Textos" "")
(command "-COLOR" "7")
(command "-TEXT" "S" "Standard" "J" "C" (list 14920 2335) 10 0 "14xTV")
(command "-LAYER" "S" "APs" "")
(command "-COLOR" "3")
(command "_.PLINE" (list 14940.0 3320) (list 14960.0 3320) (list 14950 3345) (list 14940.0 3320) "")
(command "_.CIRCLE" (list 14950 3345) 10)
(command "_.CIRCLE" (list 14950 3345) 21.25)
(command "_.CIRCLE" (list 14950 3345) 30)
(command "-LAYER" "S" "Textos" "")
(command "-COLOR" "7")
(command "-TEXT" "S" "Standard" "J" "C" (list 14920 3335) 10 0 "6xAP")
(command "-LAYER" "S" "Telefonos" "")
(command "-COLOR" "4")
(command "_.PLINE" (list 14940.0 3400) (list 14960.0 3400) (list 14960.0 3430) (list 14940.0 3430) "C")
(command "_.CIRCLE" (list 14950 3437) 5)
(command "-LAYER" "S" "Textos" "")
(command "-COLOR" "7")
(command "-TEXT" "S" "Standard" "J" "C" (list 14920 3415) 10 0 "3xTEL")
(command "-LAYER" "S" "TVs" "")
(command "-COLOR" "5")
(command "_.PLINE" (list 14930.0 3480) (list 14970.0 3480) (list 14970.0 3505) (list 14930.0 3505) "C")
(command "_.PLINE" (list 14940.0 3480) (list 14960.0 3480) (list 14950 3470) (list 14940.0 3480) "")
(command "-LAYER" "S" "Textos" "")
(command "-COLOR" "7")
(command "-TEXT" "S" "Standard" "J" "C" (list 14920 3495) 10 0 "9xTV")
(command "-LAYER" "S" "APs" "")
(command "-COLOR" "3")
(command "_.PLINE" (list 14940.0 4400) (list 14960.0 4400) (list 14950 4425) (list 14940.0 4400) "")
(command "_.CIRCLE" (list 14950 4425) 10)
(command "_.CIRCLE" (list 14950 4425) 21.25)
(command "_.CIRCLE" (list 14950 4425) 30)
(command "-LAYER" "S" "Textos" "")
(command "-COLOR" "7")
(command "-TEXT" "S" "Standard" "J" "C" (list 14920 4415) 10 0 "6xAP")
(command "-LAYER" "S" "Telefonos" "")
(command "-COLOR" "4")
(command "_.PLINE" (list 14940.0 4480) (list 14960.0 4480) (list 14960.0 4510) (list 14940.0 4510) "C")
(command "_.CIRCLE" (list 14950 4517) 5)
(command "-LAYER" "S" "Textos" "")
(command "-COLOR" "7")
(command "-TEXT" "S" "Standard" "J" "C" (list 14920 4495) 10 0 "3xTEL")
(command "-LAYER" "S" "TVs" "")
(command "-COLOR" "5")
(command "_.PLINE" (list 14930.0 4560) (list 14970.0 4560) (list 14970.0 4585) (list 14930.0 4585) "C")
(command "_.PLINE" (list 14940.0 4560) (list 14960.0 4560) (list 14950 4550) (list 14940.0 4560) "")
(command "-LAYER" "S" "Textos" "")
(command "-COLOR" "7")
(command "-TEXT" "S" "Standard" "J" "C" (list 14920 4575) 10 0 "11xTV")
(command "-LAYER" "S" "APs" "")
(command "-COLOR" "3")
(command "_.PLINE" (list 14940.0 5400) (list 14960.0 5400) (list 14950 5425) (list 14940.0 5400) "")
(command "_.CIRCLE" (list 14950 5425) 10)
(command "_.CIRCLE" (list 14950 5425) 21.25)
(command "_.CIRCLE" (list 14950 5425) 30)
(command "-LAYER" "S" "Textos" "")
(command "-COLOR" "7")
(command "-TEXT" "S" "Standard" "J" "C" (list 14920 5415) 10 0 "7xAP")
(command "-LAYER" "S" "Telefonos" "")
(command "-COLOR" "4")
(command "_.PLINE" (list 14940.0 5480) (list 14960.0 5480) (list 14960.0 5510) (list 14940.0 5510) "C")
(command "_.CIRCLE" (list 14950 5517) 5)
(command "-LAYER" "S" "Textos" "")
(command "-COLOR" "7")
(command "-TEXT" "S" "Standard" "J" "C" (list 14920 5495) 10 0 "3xTEL")
(command "-LAYER" "S" "TVs" "")
(command "-COLOR" "5")
(command "_.PLINE" (list 14930.0 5560) (list 14970.0 5560) (list 14970.0 5585) (list 14930.0 5585) "C")
(command "_.PLINE" (list 14940.0 5560) (list 14960.0 5560) (list 14950 5550) (list 14940.0 5560) "")
(command "-LAYER" "S" "Textos" "")
(command "-COLOR" "7")
(command "-TEXT" "S" "Standard" "J" "C" (list 14920 5575) 10 0 "13xTV")
(command "-LAYER" "S" "APs" "")
(command "-COLOR" "3")
(command "_.PLINE" (list 14940.0 6560) (list 14960.0 6560) (list 14950 6585) (list 14940.0 6560) "")
(command "_.CIRCLE" (list 14950 6585) 10)
(command "_.CIRCLE" (list 14950 6585) 21.25)
(command "_.CIRCLE" (list 14950 6585) 30)
(command "-LAYER" "S" "Textos" "")
(command "-COLOR" "7")
(command "-TEXT" "S" "Standard" "J" "C" (list 14920 6575) 10 0 "2xAP")
(command "-LAYER" "S" "Telefonos" "")
(command "-COLOR" "4")
(command "_.PLINE" (list 14940.0 6640) (list 14960.0 6640) (list 14960.0 6670) (list 14940.0 6670) "C")
(command "_.CIRCLE" (list 14950 6677) 5)
(command "-LAYER" "S" "Textos" "")
(command "-COLOR" "7")
(command "-TEXT" "S" "Standard" "J" "C" (list 14920 6655) 10 0 "1xTEL")
(command "-LAYER" "S" "TVs" "")
(command "-COLOR" "5")
(command "_.PLINE" (list 14930.0 6720) (list 14970.0 6720) (list 14970.0 6745) (list 14930.0 6745) "C")
(command "_.PLINE" (list 14940.0 6720) (list 14960.0 6720) (list 14950 6710) (list 14940.0 6720) "")
(command "-LAYER" "S" "Textos" "")
(command "-COLOR" "7")
(command "-TEXT" "S" "Standard" "J" "C" (list 14920 6735) 10 0 "4xTV")
(command "-LAYER" "S" "APs" "")
(command "-COLOR" "3")
(command "_.PLINE" (list 14940.0 7800) (list 14960.0 7800) (list 14950 7825) (list 14940.0 7800) "")
(command "_.CIRCLE" (list 14950 7825) 10)
(command "_.CIRCLE" (list 14950 7825) 21.25)
(command "_.CIRCLE" (list 14950 7825) 30)
(command "-LAYER" "S" "Textos" "")
(command "-COLOR" "7")
(command "-TEXT" "S" "Standard" "J" "C" (list 14920 7815) 10 0 "2xAP")
(command "-LAYER" "S" "Telefonos" "")
(command "-COLOR" "4")
(command "_.PLINE" (list 14940.0 7880) (list 14960.0 7880) (list 14960.0 7910) (list 14940.0 7910) "C")
(command "_.CIRCLE" (list 14950 7917) 5)
(command "-LAYER" "S" "Textos" "")
(command "-COLOR" "7")
(command "-TEXT" "S" "Standard" "J" "C" (list 14920 7895) 10 0 "1xTEL")
(command "-LAYER" "S" "TVs" "")
(command "-COLOR" "5")
(command "_.PLINE" (list 14930.0 7960) (list 14970.0 7960) (list 14970.0 7985) (list 14930.0 7985) "C")
(command "_.PLINE" (list 14940.0 7960) (list 14960.0 7960) (list 14950 7950) (list 14940.0 7960) "")
(command "-LAYER" "S" "Textos" "")
(command "-COLOR" "7")
(command "-TEXT" "S" "Standard" "J" "C" (list 14920 7975) 10 0 "3xTV")

; === DIBUJAR TORRE: IDF15 ===
(command "-LAYER" "S" "Textos" "")
(command "-COLOR" "7")
(command "-TEXT" "S" "Standard" "J" "C" (list 15850 150) 25 0 "IDF15")
(command "-LAYER" "S" "Switches" "")
(command "-COLOR" "6")
(command "_.PLINE" (list 15900 150) (list 16050 150) (list 16050 190) (list 15900 190) "C")
(command "-LAYER" "S" "Textos" "")
(command "-COLOR" "7")
(command "-TEXT" "S" "Standard" "J" "MC" (list 15975.0 170.0) 8 0 "SW-CCTV (DS-3E3728F)")
(command "-LAYER" "S" "Switches" "")
(command "-COLOR" "6")
(command "_.PLINE" (list 15900 250) (list 16050 250) (list 16050 290) (list 15900 290) "C")
(command "-LAYER" "S" "Textos" "")
(command "-COLOR" "7")
(command "-TEXT" "S" "Standard" "J" "MC" (list 15975.0 270.0) 8 0 "SW-DATA (Meraki MS225)")
(command "-LAYER" "S" "Switches" "")
(command "-COLOR" "6")
(command "_.PLINE" (list 15900 350) (list 16050 350) (list 16050 390) (list 15900 390) "C")
(command "-LAYER" "S" "Textos" "")
(command "-COLOR" "7")
(command "-TEXT" "S" "Standard" "J" "MC" (list 15975.0 370.0) 8 0 "SW-IPTV (RG-NBS6002)")
(command "-LAYER" "S" "Switches" "")
(command "-COLOR" "6")
(command "_.PLINE" (list 15900 450) (list 16050 450) (list 16050 490) (list 15900 490) "C")
(command "-LAYER" "S" "Textos" "")
(command "-COLOR" "7")
(command "-TEXT" "S" "Standard" "J" "MC" (list 15975.0 470.0) 8 0 "SW-TEL (Meraki MS225)")
(command "-LAYER" "S" "Switches" "")
(command "-COLOR" "6")
(command "_.PLINE" (list 15900 550) (list 16050 550) (list 16050 590) (list 15900 590) "C")
(command "-LAYER" "S" "Textos" "")
(command "-COLOR" "7")
(command "-TEXT" "S" "Standard" "J" "MC" (list 15975.0 570.0) 8 0 "SW-WIFI (Meraki MS225)")
(command "-LAYER" "S" "APs" "")
(command "-COLOR" "3")
(command "_.PLINE" (list 15990.0 840) (list 16010.0 840) (list 16000 865) (list 15990.0 840) "")
(command "_.CIRCLE" (list 16000 865) 10)
(command "_.CIRCLE" (list 16000 865) 21.25)
(command "_.CIRCLE" (list 16000 865) 30)
(command "-LAYER" "S" "Textos" "")
(command "-COLOR" "7")
(command "-TEXT" "S" "Standard" "J" "C" (list 15970 855) 10 0 "2xAP")
(command "-LAYER" "S" "Telefonos" "")
(command "-COLOR" "4")
(command "_.PLINE" (list 15990.0 920) (list 16010.0 920) (list 16010.0 950) (list 15990.0 950) "C")
(command "_.CIRCLE" (list 16000 957) 5)
(command "-LAYER" "S" "Textos" "")
(command "-COLOR" "7")
(command "-TEXT" "S" "Standard" "J" "C" (list 15970 935) 10 0 "1xTEL")
(command "-LAYER" "S" "TVs" "")
(command "-COLOR" "5")
(command "_.PLINE" (list 15980.0 1000) (list 16020.0 1000) (list 16020.0 1025) (list 15980.0 1025) "C")
(command "_.PLINE" (list 15990.0 1000) (list 16010.0 1000) (list 16000 990) (list 15990.0 1000) "")
(command "-LAYER" "S" "Textos" "")
(command "-COLOR" "7")
(command "-TEXT" "S" "Standard" "J" "C" (list 15970 1015) 10 0 "3xTV")
(command "-LAYER" "S" "APs" "")
(command "-COLOR" "3")
(command "_.PLINE" (list 15990.0 5400) (list 16010.0 5400) (list 16000 5425) (list 15990.0 5400) "")
(command "_.CIRCLE" (list 16000 5425) 10)
(command "_.CIRCLE" (list 16000 5425) 21.25)
(command "_.CIRCLE" (list 16000 5425) 30)
(command "-LAYER" "S" "Textos" "")
(command "-COLOR" "7")
(command "-TEXT" "S" "Standard" "J" "C" (list 15970 5415) 10 0 "2xAP")
(command "-LAYER" "S" "Telefonos" "")
(command "-COLOR" "4")
(command "_.PLINE" (list 15990.0 5480) (list 16010.0 5480) (list 16010.0 5510) (list 15990.0 5510) "C")
(command "_.CIRCLE" (list 16000 5517) 5)
(command "-LAYER" "S" "Textos" "")
(command "-COLOR" "7")
(command "-TEXT" "S" "Standard" "J" "C" (list 15970 5495) 10 0 "1xTEL")
(command "-LAYER" "S" "TVs" "")
(command "-COLOR" "5")
(command "_.PLINE" (list 15980.0 5560) (list 16020.0 5560) (list 16020.0 5585) (list 15980.0 5585) "C")
(command "_.PLINE" (list 15990.0 5560) (list 16010.0 5560) (list 16000 5550) (list 15990.0 5560) "")
(command "-LAYER" "S" "Textos" "")
(command "-COLOR" "7")
(command "-TEXT" "S" "Standard" "J" "C" (list 15970 5575) 10 0 "3xTV")
(command "-LAYER" "S" "APs" "")
(command "-COLOR" "3")
(command "_.PLINE" (list 15990.0 6560) (list 16010.0 6560) (list 16000 6585) (list 15990.0 6560) "")
(command "_.CIRCLE" (list 16000 6585) 10)
(command "_.CIRCLE" (list 16000 6585) 21.25)
(command "_.CIRCLE" (list 16000 6585) 30)
(command "-LAYER" "S" "Textos" "")
(command "-COLOR" "7")
(command "-TEXT" "S" "Standard" "J" "C" (list 15970 6575) 10 0 "2xAP")
(command "-LAYER" "S" "Telefonos" "")
(command "-COLOR" "4")
(command "_.PLINE" (list 15990.0 6640) (list 16010.0 6640) (list 16010.0 6670) (list 15990.0 6670) "C")
(command "_.CIRCLE" (list 16000 6677) 5)
(command "-LAYER" "S" "Textos" "")
(command "-COLOR" "7")
(command "-TEXT" "S" "Standard" "J" "C" (list 15970 6655) 10 0 "1xTEL")
(command "-LAYER" "S" "TVs" "")
(command "-COLOR" "5")
(command "_.PLINE" (list 15980.0 6720) (list 16020.0 6720) (list 16020.0 6745) (list 15980.0 6745) "C")
(command "_.PLINE" (list 15990.0 6720) (list 16010.0 6720) (list 16000 6710) (list 15990.0 6720) "")
(command "-LAYER" "S" "Textos" "")
(command "-COLOR" "7")
(command "-TEXT" "S" "Standard" "J" "C" (list 15970 6735) 10 0 "3xTV")
(command "-LAYER" "S" "APs" "")
(command "-COLOR" "3")
(command "_.PLINE" (list 15990.0 7800) (list 16010.0 7800) (list 16000 7825) (list 15990.0 7800) "")
(command "_.CIRCLE" (list 16000 7825) 10)
(command "_.CIRCLE" (list 16000 7825) 21.25)
(command "_.CIRCLE" (list 16000 7825) 30)
(command "-LAYER" "S" "Textos" "")
(command "-COLOR" "7")
(command "-TEXT" "S" "Standard" "J" "C" (list 15970 7815) 10 0 "8xAP")
(command "-LAYER" "S" "Telefonos" "")
(command "-COLOR" "4")
(command "_.PLINE" (list 15990.0 7880) (list 16010.0 7880) (list 16010.0 7910) (list 15990.0 7910) "C")
(command "_.CIRCLE" (list 16000 7917) 5)
(command "-LAYER" "S" "Textos" "")
(command "-COLOR" "7")
(command "-TEXT" "S" "Standard" "J" "C" (list 15970 7895) 10 0 "3xTEL")
(command "-LAYER" "S" "TVs" "")
(command "-COLOR" "5")
(command "_.PLINE" (list 15980.0 7960) (list 16020.0 7960) (list 16020.0 7985) (list 15980.0 7985) "C")
(command "_.PLINE" (list 15990.0 7960) (list 16010.0 7960) (list 16000 7950) (list 15990.0 7960) "")
(command "-LAYER" "S" "Textos" "")
(command "-COLOR" "7")
(command "-TEXT" "S" "Standard" "J" "C" (list 15970 7975) 10 0 "13xTV")

; === DIBUJAR LÍNEAS DE NIVEL ===
(command "-LAYER" "S" "Niveles" "")
(command "-COLOR" "8")
(command "_.LINE" (list 50 100) (list 16350 100) "")
(command "-LAYER" "S" "Textos" "")
(command "-COLOR" "7")
(command "-TEXT" "S" "Standard" "J" "L" (list 60 110) 15 0 "SOTANO")
(command "-LAYER" "S" "Niveles" "")
(command "-COLOR" "8")
(command "_.LINE" (list 50 790) (list 16350 790) "")
(command "-LAYER" "S" "Textos" "")
(command "-COLOR" "7")
(command "-TEXT" "S" "Standard" "J" "L" (list 60 800) 15 0 "NIVEL 1")
(command "-LAYER" "S" "Niveles" "")
(command "-COLOR" "8")
(command "_.LINE" (list 50 2110) (list 16350 2110) "")
(command "-LAYER" "S" "Textos" "")
(command "-COLOR" "7")
(command "-TEXT" "S" "Standard" "J" "L" (list 60 2120) 15 0 "NIVEL 2")
(command "-LAYER" "S" "Niveles" "")
(command "-COLOR" "8")
(command "_.LINE" (list 50 3270) (list 16350 3270) "")
(command "-LAYER" "S" "Textos" "")
(command "-COLOR" "7")
(command "-TEXT" "S" "Standard" "J" "L" (list 60 3280) 15 0 "NIVEL 3")
(command "-LAYER" "S" "Niveles" "")
(command "-COLOR" "8")
(command "_.LINE" (list 50 4350) (list 16350 4350) "")
(command "-LAYER" "S" "Textos" "")
(command "-COLOR" "7")
(command "-TEXT" "S" "Standard" "J" "L" (list 60 4360) 15 0 "NIVEL 4")
(command "-LAYER" "S" "Niveles" "")
(command "-COLOR" "8")
(command "_.LINE" (list 50 5350) (list 16350 5350) "")
(command "-LAYER" "S" "Textos" "")
(command "-COLOR" "7")
(command "-TEXT" "S" "Standard" "J" "L" (list 60 5360) 15 0 "NIVEL 5")
(command "-LAYER" "S" "Niveles" "")
(command "-COLOR" "8")
(command "_.LINE" (list 50 6510) (list 16350 6510) "")
(command "-LAYER" "S" "Textos" "")
(command "-COLOR" "7")
(command "-TEXT" "S" "Standard" "J" "L" (list 60 6520) 15 0 "NIVEL 6")
(command "-LAYER" "S" "Niveles" "")
(command "-COLOR" "8")
(command "_.LINE" (list 50 7750) (list 16350 7750) "")
(command "-LAYER" "S" "Textos" "")
(command "-COLOR" "7")
(command "-TEXT" "S" "Standard" "J" "L" (list 60 7760) 15 0 "NIVEL 7")

; === DIBUJAR CABLES UTP ===
(princ "\nDibujando cables UTP...")
(command "-LAYER" "S" "Cables_UTP" "")
(command "-COLOR" "5")
(command "-LAYER" "S" "Cables_UTP" "")
(command "-COLOR" "5")
(command "-LAYER" "S" "Cables_UTP" "")
(command "-COLOR" "5")
(command "-LAYER" "S" "Cables_UTP" "")
(command "-COLOR" "5")
(command "_.PLINE" (list 1275.0 590) (list 1275.0 600) (list 1275.0 8090) "")
(command "_.LINE" (list 1275.0 8090) (list 1300 8090) "")
(command "_.LINE" (list 1300 8090) (list 1300 5400) "")
(command "_.LINE" (list 1300 8090) (list 1300 2160) "")
(command "_.LINE" (list 1300 8090) (list 1300 7800) "")
(command "_.LINE" (list 1300 8090) (list 1300 3320) "")
(command "_.LINE" (list 1300 8090) (list 1300 840) "")
(command "_.LINE" (list 1300 8090) (list 1300 4400) "")
(command "_.LINE" (list 1300 8090) (list 1300 6560) "")
(command "-LAYER" "S" "Cables_UTP" "")
(command "-COLOR" "5")
(command "_.PLINE" (list 1275.0 490) (list 1275.0 500) (list 1275.0 8120) "")
(command "_.LINE" (list 1275.0 8120) (list 1300 8120) "")
(command "_.LINE" (list 1300 8120) (list 1300 5480) "")
(command "_.LINE" (list 1300 8120) (list 1300 2240) "")
(command "_.LINE" (list 1300 8120) (list 1300 7880) "")
(command "_.LINE" (list 1300 8120) (list 1300 3400) "")
(command "_.LINE" (list 1300 8120) (list 1300 920) "")
(command "_.LINE" (list 1300 8120) (list 1300 4480) "")
(command "_.LINE" (list 1300 8120) (list 1300 6640) "")
(command "-LAYER" "S" "Cables_UTP" "")
(command "-COLOR" "5")
(command "_.PLINE" (list 1275.0 390) (list 1275.0 400) (list 1275.0 8150) "")
(command "_.LINE" (list 1275.0 8150) (list 1300 8150) "")
(command "_.LINE" (list 1300 8150) (list 1300 5560) "")
(command "_.LINE" (list 1300 8150) (list 1300 2320) "")
(command "_.LINE" (list 1300 8150) (list 1300 7960) "")
(command "_.LINE" (list 1300 8150) (list 1300 3480) "")
(command "_.LINE" (list 1300 8150) (list 1300 1000) "")
(command "_.LINE" (list 1300 8150) (list 1300 4560) "")
(command "_.LINE" (list 1300 8150) (list 1300 6720) "")
(command "-LAYER" "S" "Cables_UTP" "")
(command "-COLOR" "5")
(command "_.PLINE" (list 2325.0 590) (list 2325.0 600) (list 2325.0 8090) "")
(command "_.LINE" (list 2325.0 8090) (list 2350 8090) "")
(command "_.LINE" (list 2350 8090) (list 2350 3320) "")
(command "_.LINE" (list 2350 8090) (list 2350 5400) "")
(command "_.LINE" (list 2350 8090) (list 2350 4400) "")
(command "_.LINE" (list 2350 8090) (list 2350 6560) "")
(command "_.LINE" (list 2350 8090) (list 2350 7800) "")
(command "-LAYER" "S" "Cables_UTP" "")
(command "-COLOR" "5")
(command "_.PLINE" (list 2325.0 490) (list 2325.0 500) (list 2325.0 8120) "")
(command "_.LINE" (list 2325.0 8120) (list 2350 8120) "")
(command "_.LINE" (list 2350 8120) (list 2350 3400) "")
(command "_.LINE" (list 2350 8120) (list 2350 5480) "")
(command "_.LINE" (list 2350 8120) (list 2350 4480) "")
(command "_.LINE" (list 2350 8120) (list 2350 6640) "")
(command "_.LINE" (list 2350 8120) (list 2350 7880) "")
(command "-LAYER" "S" "Cables_UTP" "")
(command "-COLOR" "5")
(command "_.PLINE" (list 2325.0 390) (list 2325.0 400) (list 2325.0 8150) "")
(command "_.LINE" (list 2325.0 8150) (list 2350 8150) "")
(command "_.LINE" (list 2350 8150) (list 2350 3480) "")
(command "_.LINE" (list 2350 8150) (list 2350 5560) "")
(command "_.LINE" (list 2350 8150) (list 2350 4560) "")
(command "_.LINE" (list 2350 8150) (list 2350 6720) "")
(command "_.LINE" (list 2350 8150) (list 2350 7960) "")
(command "-LAYER" "S" "Cables_UTP" "")
(command "-COLOR" "5")
(command "_.PLINE" (list 3375.0 590) (list 3375.0 600) (list 3375.0 8090) "")
(command "_.LINE" (list 3375.0 8090) (list 3400 8090) "")
(command "_.LINE" (list 3400 8090) (list 3400 840) "")
(command "_.LINE" (list 3400 8090) (list 3400 7800) "")
(command "_.LINE" (list 3400 8090) (list 3400 2160) "")
(command "_.LINE" (list 3400 8090) (list 3400 3320) "")
(command "_.LINE" (list 3400 8090) (list 3400 6560) "")
(command "_.LINE" (list 3400 8090) (list 3400 4400) "")
(command "_.LINE" (list 3400 8090) (list 3400 5400) "")
(command "-LAYER" "S" "Cables_UTP" "")
(command "-COLOR" "5")
(command "_.PLINE" (list 3375.0 490) (list 3375.0 500) (list 3375.0 8120) "")
(command "_.LINE" (list 3375.0 8120) (list 3400 8120) "")
(command "_.LINE" (list 3400 8120) (list 3400 920) "")
(command "_.LINE" (list 3400 8120) (list 3400 7880) "")
(command "_.LINE" (list 3400 8120) (list 3400 2240) "")
(command "_.LINE" (list 3400 8120) (list 3400 3400) "")
(command "_.LINE" (list 3400 8120) (list 3400 6640) "")
(command "_.LINE" (list 3400 8120) (list 3400 4480) "")
(command "_.LINE" (list 3400 8120) (list 3400 5480) "")
(command "-LAYER" "S" "Cables_UTP" "")
(command "-COLOR" "5")
(command "_.PLINE" (list 3375.0 390) (list 3375.0 400) (list 3375.0 8150) "")
(command "_.LINE" (list 3375.0 8150) (list 3400 8150) "")
(command "_.LINE" (list 3400 8150) (list 3400 1000) "")
(command "_.LINE" (list 3400 8150) (list 3400 7960) "")
(command "_.LINE" (list 3400 8150) (list 3400 2320) "")
(command "_.LINE" (list 3400 8150) (list 3400 3480) "")
(command "_.LINE" (list 3400 8150) (list 3400 6720) "")
(command "_.LINE" (list 3400 8150) (list 3400 4560) "")
(command "_.LINE" (list 3400 8150) (list 3400 5560) "")
(command "-LAYER" "S" "Cables_UTP" "")
(command "-COLOR" "5")
(command "_.PLINE" (list 4425.0 590) (list 4425.0 600) (list 4425.0 8090) "")
(command "_.LINE" (list 4425.0 8090) (list 4450 8090) "")
(command "_.LINE" (list 4450 8090) (list 4450 840) "")
(command "_.LINE" (list 4450 8090) (list 4450 5400) "")
(command "_.LINE" (list 4450 8090) (list 4450 4400) "")
(command "_.LINE" (list 4450 8090) (list 4450 3320) "")
(command "_.LINE" (list 4450 8090) (list 4450 2160) "")
(command "_.LINE" (list 4450 8090) (list 4450 6560) "")
(command "_.LINE" (list 4450 8090) (list 4450 7800) "")
(command "-LAYER" "S" "Cables_UTP" "")
(command "-COLOR" "5")
(command "_.PLINE" (list 4425.0 490) (list 4425.0 500) (list 4425.0 8120) "")
(command "_.LINE" (list 4425.0 8120) (list 4450 8120) "")
(command "_.LINE" (list 4450 8120) (list 4450 920) "")
(command "_.LINE" (list 4450 8120) (list 4450 5480) "")
(command "_.LINE" (list 4450 8120) (list 4450 4480) "")
(command "_.LINE" (list 4450 8120) (list 4450 3400) "")
(command "_.LINE" (list 4450 8120) (list 4450 2240) "")
(command "_.LINE" (list 4450 8120) (list 4450 6640) "")
(command "_.LINE" (list 4450 8120) (list 4450 7880) "")
(command "-LAYER" "S" "Cables_UTP" "")
(command "-COLOR" "5")
(command "_.PLINE" (list 4425.0 390) (list 4425.0 400) (list 4425.0 8150) "")
(command "_.LINE" (list 4425.0 8150) (list 4450 8150) "")
(command "_.LINE" (list 4450 8150) (list 4450 1000) "")
(command "_.LINE" (list 4450 8150) (list 4450 5560) "")
(command "_.LINE" (list 4450 8150) (list 4450 4560) "")
(command "_.LINE" (list 4450 8150) (list 4450 3480) "")
(command "_.LINE" (list 4450 8150) (list 4450 2320) "")
(command "_.LINE" (list 4450 8150) (list 4450 6720) "")
(command "_.LINE" (list 4450 8150) (list 4450 7960) "")
(command "-LAYER" "S" "Cables_UTP" "")
(command "-COLOR" "5")
(command "_.PLINE" (list 5475.0 590) (list 5475.0 600) (list 5475.0 8090) "")
(command "_.LINE" (list 5475.0 8090) (list 5500 8090) "")
(command "_.LINE" (list 5500 8090) (list 5500 5400) "")
(command "_.LINE" (list 5500 8090) (list 5500 3320) "")
(command "_.LINE" (list 5500 8090) (list 5500 2160) "")
(command "_.LINE" (list 5500 8090) (list 5500 7800) "")
(command "_.LINE" (list 5500 8090) (list 5500 4400) "")
(command "_.LINE" (list 5500 8090) (list 5500 840) "")
(command "-LAYER" "S" "Cables_UTP" "")
(command "-COLOR" "5")
(command "_.PLINE" (list 5475.0 490) (list 5475.0 500) (list 5475.0 8120) "")
(command "_.LINE" (list 5475.0 8120) (list 5500 8120) "")
(command "_.LINE" (list 5500 8120) (list 5500 5480) "")
(command "_.LINE" (list 5500 8120) (list 5500 3400) "")
(command "_.LINE" (list 5500 8120) (list 5500 2240) "")
(command "_.LINE" (list 5500 8120) (list 5500 7880) "")
(command "_.LINE" (list 5500 8120) (list 5500 4480) "")
(command "_.LINE" (list 5500 8120) (list 5500 920) "")
(command "-LAYER" "S" "Cables_UTP" "")
(command "-COLOR" "5")
(command "_.PLINE" (list 5475.0 390) (list 5475.0 400) (list 5475.0 8150) "")
(command "_.LINE" (list 5475.0 8150) (list 5500 8150) "")
(command "_.LINE" (list 5500 8150) (list 5500 5560) "")
(command "_.LINE" (list 5500 8150) (list 5500 3480) "")
(command "_.LINE" (list 5500 8150) (list 5500 2320) "")
(command "_.LINE" (list 5500 8150) (list 5500 7960) "")
(command "_.LINE" (list 5500 8150) (list 5500 4560) "")
(command "_.LINE" (list 5500 8150) (list 5500 1000) "")
(command "-LAYER" "S" "Cables_UTP" "")
(command "-COLOR" "5")
(command "_.PLINE" (list 6525.0 590) (list 6525.0 600) (list 6525.0 8090) "")
(command "_.LINE" (list 6525.0 8090) (list 6550 8090) "")
(command "_.LINE" (list 6550 8090) (list 6550 7800) "")
(command "_.LINE" (list 6550 8090) (list 6550 840) "")
(command "_.LINE" (list 6550 8090) (list 6550 3320) "")
(command "_.LINE" (list 6550 8090) (list 6550 6560) "")
(command "_.LINE" (list 6550 8090) (list 6550 5400) "")
(command "_.LINE" (list 6550 8090) (list 6550 2160) "")
(command "-LAYER" "S" "Cables_UTP" "")
(command "-COLOR" "5")
(command "_.PLINE" (list 6525.0 490) (list 6525.0 500) (list 6525.0 8120) "")
(command "_.LINE" (list 6525.0 8120) (list 6550 8120) "")
(command "_.LINE" (list 6550 8120) (list 6550 7880) "")
(command "_.LINE" (list 6550 8120) (list 6550 920) "")
(command "_.LINE" (list 6550 8120) (list 6550 3400) "")
(command "_.LINE" (list 6550 8120) (list 6550 6640) "")
(command "_.LINE" (list 6550 8120) (list 6550 5480) "")
(command "_.LINE" (list 6550 8120) (list 6550 2240) "")
(command "-LAYER" "S" "Cables_UTP" "")
(command "-COLOR" "5")
(command "_.PLINE" (list 6525.0 390) (list 6525.0 400) (list 6525.0 8150) "")
(command "_.LINE" (list 6525.0 8150) (list 6550 8150) "")
(command "_.LINE" (list 6550 8150) (list 6550 7960) "")
(command "_.LINE" (list 6550 8150) (list 6550 1000) "")
(command "_.LINE" (list 6550 8150) (list 6550 3480) "")
(command "_.LINE" (list 6550 8150) (list 6550 6720) "")
(command "_.LINE" (list 6550 8150) (list 6550 5560) "")
(command "_.LINE" (list 6550 8150) (list 6550 2320) "")
(command "-LAYER" "S" "Cables_UTP" "")
(command "-COLOR" "5")
(command "_.PLINE" (list 7575.0 590) (list 7575.0 600) (list 7575.0 8090) "")
(command "_.LINE" (list 7575.0 8090) (list 7600 8090) "")
(command "_.LINE" (list 7600 8090) (list 7600 7800) "")
(command "_.LINE" (list 7600 8090) (list 7600 840) "")
(command "_.LINE" (list 7600 8090) (list 7600 6560) "")
(command "_.LINE" (list 7600 8090) (list 7600 4400) "")
(command "_.LINE" (list 7600 8090) (list 7600 5400) "")
(command "-LAYER" "S" "Cables_UTP" "")
(command "-COLOR" "5")
(command "_.PLINE" (list 7575.0 490) (list 7575.0 500) (list 7575.0 8120) "")
(command "_.LINE" (list 7575.0 8120) (list 7600 8120) "")
(command "_.LINE" (list 7600 8120) (list 7600 7880) "")
(command "_.LINE" (list 7600 8120) (list 7600 920) "")
(command "_.LINE" (list 7600 8120) (list 7600 6640) "")
(command "_.LINE" (list 7600 8120) (list 7600 4480) "")
(command "_.LINE" (list 7600 8120) (list 7600 5480) "")
(command "-LAYER" "S" "Cables_UTP" "")
(command "-COLOR" "5")
(command "_.PLINE" (list 7575.0 390) (list 7575.0 400) (list 7575.0 8150) "")
(command "_.LINE" (list 7575.0 8150) (list 7600 8150) "")
(command "_.LINE" (list 7600 8150) (list 7600 7960) "")
(command "_.LINE" (list 7600 8150) (list 7600 1000) "")
(command "_.LINE" (list 7600 8150) (list 7600 6720) "")
(command "_.LINE" (list 7600 8150) (list 7600 4560) "")
(command "_.LINE" (list 7600 8150) (list 7600 5560) "")
(command "-LAYER" "S" "Cables_UTP" "")
(command "-COLOR" "5")
(command "_.PLINE" (list 8625.0 590) (list 8625.0 600) (list 8625.0 8090) "")
(command "_.LINE" (list 8625.0 8090) (list 8650 8090) "")
(command "_.LINE" (list 8650 8090) (list 8650 3320) "")
(command "_.LINE" (list 8650 8090) (list 8650 5400) "")
(command "_.LINE" (list 8650 8090) (list 8650 2160) "")
(command "_.LINE" (list 8650 8090) (list 8650 6560) "")
(command "_.LINE" (list 8650 8090) (list 8650 7800) "")
(command "_.LINE" (list 8650 8090) (list 8650 840) "")
(command "-LAYER" "S" "Cables_UTP" "")
(command "-COLOR" "5")
(command "_.PLINE" (list 8625.0 490) (list 8625.0 500) (list 8625.0 8120) "")
(command "_.LINE" (list 8625.0 8120) (list 8650 8120) "")
(command "_.LINE" (list 8650 8120) (list 8650 3400) "")
(command "_.LINE" (list 8650 8120) (list 8650 5480) "")
(command "_.LINE" (list 8650 8120) (list 8650 2240) "")
(command "_.LINE" (list 8650 8120) (list 8650 6640) "")
(command "_.LINE" (list 8650 8120) (list 8650 7880) "")
(command "_.LINE" (list 8650 8120) (list 8650 920) "")
(command "-LAYER" "S" "Cables_UTP" "")
(command "-COLOR" "5")
(command "_.PLINE" (list 8625.0 390) (list 8625.0 400) (list 8625.0 8150) "")
(command "_.LINE" (list 8625.0 8150) (list 8650 8150) "")
(command "_.LINE" (list 8650 8150) (list 8650 3480) "")
(command "_.LINE" (list 8650 8150) (list 8650 5560) "")
(command "_.LINE" (list 8650 8150) (list 8650 2320) "")
(command "_.LINE" (list 8650 8150) (list 8650 6720) "")
(command "_.LINE" (list 8650 8150) (list 8650 7960) "")
(command "_.LINE" (list 8650 8150) (list 8650 1000) "")
(command "-LAYER" "S" "Cables_UTP" "")
(command "-COLOR" "5")
(command "_.PLINE" (list 9675.0 590) (list 9675.0 600) (list 9675.0 8090) "")
(command "_.LINE" (list 9675.0 8090) (list 9700 8090) "")
(command "_.LINE" (list 9700 8090) (list 9700 3320) "")
(command "_.LINE" (list 9700 8090) (list 9700 840) "")
(command "_.LINE" (list 9700 8090) (list 9700 7800) "")
(command "_.LINE" (list 9700 8090) (list 9700 6560) "")
(command "_.LINE" (list 9700 8090) (list 9700 2160) "")
(command "_.LINE" (list 9700 8090) (list 9700 5400) "")
(command "_.LINE" (list 9700 8090) (list 9700 4400) "")
(command "-LAYER" "S" "Cables_UTP" "")
(command "-COLOR" "5")
(command "_.PLINE" (list 9675.0 490) (list 9675.0 500) (list 9675.0 8120) "")
(command "_.LINE" (list 9675.0 8120) (list 9700 8120) "")
(command "_.LINE" (list 9700 8120) (list 9700 3400) "")
(command "_.LINE" (list 9700 8120) (list 9700 920) "")
(command "_.LINE" (list 9700 8120) (list 9700 7880) "")
(command "_.LINE" (list 9700 8120) (list 9700 6640) "")
(command "_.LINE" (list 9700 8120) (list 9700 2240) "")
(command "_.LINE" (list 9700 8120) (list 9700 5480) "")
(command "_.LINE" (list 9700 8120) (list 9700 4480) "")
(command "-LAYER" "S" "Cables_UTP" "")
(command "-COLOR" "5")
(command "_.PLINE" (list 9675.0 390) (list 9675.0 400) (list 9675.0 8150) "")
(command "_.LINE" (list 9675.0 8150) (list 9700 8150) "")
(command "_.LINE" (list 9700 8150) (list 9700 3480) "")
(command "_.LINE" (list 9700 8150) (list 9700 1000) "")
(command "_.LINE" (list 9700 8150) (list 9700 7960) "")
(command "_.LINE" (list 9700 8150) (list 9700 6720) "")
(command "_.LINE" (list 9700 8150) (list 9700 2320) "")
(command "_.LINE" (list 9700 8150) (list 9700 5560) "")
(command "_.LINE" (list 9700 8150) (list 9700 4560) "")
(command "-LAYER" "S" "Cables_UTP" "")
(command "-COLOR" "5")
(command "_.PLINE" (list 10725.0 590) (list 10725.0 600) (list 10725.0 8090) "")
(command "_.LINE" (list 10725.0 8090) (list 10750 8090) "")
(command "_.LINE" (list 10750 8090) (list 10750 2160) "")
(command "_.LINE" (list 10750 8090) (list 10750 840) "")
(command "_.LINE" (list 10750 8090) (list 10750 6560) "")
(command "_.LINE" (list 10750 8090) (list 10750 4400) "")
(command "_.LINE" (list 10750 8090) (list 10750 5400) "")
(command "_.LINE" (list 10750 8090) (list 10750 7800) "")
(command "-LAYER" "S" "Cables_UTP" "")
(command "-COLOR" "5")
(command "_.PLINE" (list 10725.0 490) (list 10725.0 500) (list 10725.0 8120) "")
(command "_.LINE" (list 10725.0 8120) (list 10750 8120) "")
(command "_.LINE" (list 10750 8120) (list 10750 2240) "")
(command "_.LINE" (list 10750 8120) (list 10750 920) "")
(command "_.LINE" (list 10750 8120) (list 10750 6640) "")
(command "_.LINE" (list 10750 8120) (list 10750 4480) "")
(command "_.LINE" (list 10750 8120) (list 10750 5480) "")
(command "_.LINE" (list 10750 8120) (list 10750 7880) "")
(command "-LAYER" "S" "Cables_UTP" "")
(command "-COLOR" "5")
(command "_.PLINE" (list 10725.0 390) (list 10725.0 400) (list 10725.0 8150) "")
(command "_.LINE" (list 10725.0 8150) (list 10750 8150) "")
(command "_.LINE" (list 10750 8150) (list 10750 2320) "")
(command "_.LINE" (list 10750 8150) (list 10750 1000) "")
(command "_.LINE" (list 10750 8150) (list 10750 6720) "")
(command "_.LINE" (list 10750 8150) (list 10750 4560) "")
(command "_.LINE" (list 10750 8150) (list 10750 5560) "")
(command "_.LINE" (list 10750 8150) (list 10750 7960) "")
(command "-LAYER" "S" "Cables_UTP" "")
(command "-COLOR" "5")
(command "_.PLINE" (list 11775.0 590) (list 11775.0 600) (list 11775.0 8090) "")
(command "_.LINE" (list 11775.0 8090) (list 11800 8090) "")
(command "_.LINE" (list 11800 8090) (list 11800 3320) "")
(command "_.LINE" (list 11800 8090) (list 11800 7800) "")
(command "_.LINE" (list 11800 8090) (list 11800 2160) "")
(command "_.LINE" (list 11800 8090) (list 11800 840) "")
(command "_.LINE" (list 11800 8090) (list 11800 6560) "")
(command "-LAYER" "S" "Cables_UTP" "")
(command "-COLOR" "5")
(command "_.PLINE" (list 11775.0 490) (list 11775.0 500) (list 11775.0 8120) "")
(command "_.LINE" (list 11775.0 8120) (list 11800 8120) "")
(command "_.LINE" (list 11800 8120) (list 11800 3400) "")
(command "_.LINE" (list 11800 8120) (list 11800 7880) "")
(command "_.LINE" (list 11800 8120) (list 11800 2240) "")
(command "_.LINE" (list 11800 8120) (list 11800 920) "")
(command "_.LINE" (list 11800 8120) (list 11800 6640) "")
(command "-LAYER" "S" "Cables_UTP" "")
(command "-COLOR" "5")
(command "_.PLINE" (list 11775.0 390) (list 11775.0 400) (list 11775.0 8150) "")
(command "_.LINE" (list 11775.0 8150) (list 11800 8150) "")
(command "_.LINE" (list 11800 8150) (list 11800 3480) "")
(command "_.LINE" (list 11800 8150) (list 11800 7960) "")
(command "_.LINE" (list 11800 8150) (list 11800 2320) "")
(command "_.LINE" (list 11800 8150) (list 11800 1000) "")
(command "_.LINE" (list 11800 8150) (list 11800 6720) "")
(command "-LAYER" "S" "Cables_UTP" "")
(command "-COLOR" "5")
(command "_.PLINE" (list 12825.0 590) (list 12825.0 600) (list 12825.0 2450) "")
(command "_.LINE" (list 12825.0 2450) (list 12850 2450) "")
(command "_.LINE" (list 12850 2450) (list 12850 2160) "")
(command "_.LINE" (list 12850 2450) (list 12850 840) "")
(command "-LAYER" "S" "Cables_UTP" "")
(command "-COLOR" "5")
(command "_.PLINE" (list 12825.0 490) (list 12825.0 500) (list 12825.0 2480) "")
(command "_.LINE" (list 12825.0 2480) (list 12850 2480) "")
(command "_.LINE" (list 12850 2480) (list 12850 2240) "")
(command "_.LINE" (list 12850 2480) (list 12850 920) "")
(command "-LAYER" "S" "Cables_UTP" "")
(command "-COLOR" "5")
(command "_.PLINE" (list 12825.0 390) (list 12825.0 400) (list 12825.0 2510) "")
(command "_.LINE" (list 12825.0 2510) (list 12850 2510) "")
(command "_.LINE" (list 12850 2510) (list 12850 2320) "")
(command "_.LINE" (list 12850 2510) (list 12850 1000) "")
(command "-LAYER" "S" "Cables_UTP" "")
(command "-COLOR" "5")
(command "_.PLINE" (list 13875.0 590) (list 13875.0 600) (list 13875.0 8090) "")
(command "_.LINE" (list 13875.0 8090) (list 13900 8090) "")
(command "_.LINE" (list 13900 8090) (list 13900 7800) "")
(command "_.LINE" (list 13900 8090) (list 13900 6560) "")
(command "_.LINE" (list 13900 8090) (list 13900 4400) "")
(command "_.LINE" (list 13900 8090) (list 13900 3320) "")
(command "_.LINE" (list 13900 8090) (list 13900 2160) "")
(command "_.LINE" (list 13900 8090) (list 13900 840) "")
(command "-LAYER" "S" "Cables_UTP" "")
(command "-COLOR" "5")
(command "_.PLINE" (list 13875.0 490) (list 13875.0 500) (list 13875.0 8120) "")
(command "_.LINE" (list 13875.0 8120) (list 13900 8120) "")
(command "_.LINE" (list 13900 8120) (list 13900 7880) "")
(command "_.LINE" (list 13900 8120) (list 13900 6640) "")
(command "_.LINE" (list 13900 8120) (list 13900 4480) "")
(command "_.LINE" (list 13900 8120) (list 13900 3400) "")
(command "_.LINE" (list 13900 8120) (list 13900 2240) "")
(command "_.LINE" (list 13900 8120) (list 13900 920) "")
(command "-LAYER" "S" "Cables_UTP" "")
(command "-COLOR" "5")
(command "_.PLINE" (list 13875.0 390) (list 13875.0 400) (list 13875.0 8150) "")
(command "_.LINE" (list 13875.0 8150) (list 13900 8150) "")
(command "_.LINE" (list 13900 8150) (list 13900 7960) "")
(command "_.LINE" (list 13900 8150) (list 13900 6720) "")
(command "_.LINE" (list 13900 8150) (list 13900 4560) "")
(command "_.LINE" (list 13900 8150) (list 13900 3480) "")
(command "_.LINE" (list 13900 8150) (list 13900 2320) "")
(command "_.LINE" (list 13900 8150) (list 13900 1000) "")
(command "-LAYER" "S" "Cables_UTP" "")
(command "-COLOR" "5")
(command "_.PLINE" (list 14925.0 590) (list 14925.0 600) (list 14925.0 8090) "")
(command "_.LINE" (list 14925.0 8090) (list 14950 8090) "")
(command "_.LINE" (list 14950 8090) (list 14950 4400) "")
(command "_.LINE" (list 14950 8090) (list 14950 2160) "")
(command "_.LINE" (list 14950 8090) (list 14950 5400) "")
(command "_.LINE" (list 14950 8090) (list 14950 6560) "")
(command "_.LINE" (list 14950 8090) (list 14950 7800) "")
(command "_.LINE" (list 14950 8090) (list 14950 3320) "")
(command "_.LINE" (list 14950 8090) (list 14950 840) "")
(command "-LAYER" "S" "Cables_UTP" "")
(command "-COLOR" "5")
(command "_.PLINE" (list 14925.0 490) (list 14925.0 500) (list 14925.0 8120) "")
(command "_.LINE" (list 14925.0 8120) (list 14950 8120) "")
(command "_.LINE" (list 14950 8120) (list 14950 4480) "")
(command "_.LINE" (list 14950 8120) (list 14950 2240) "")
(command "_.LINE" (list 14950 8120) (list 14950 5480) "")
(command "_.LINE" (list 14950 8120) (list 14950 6640) "")
(command "_.LINE" (list 14950 8120) (list 14950 7880) "")
(command "_.LINE" (list 14950 8120) (list 14950 3400) "")
(command "_.LINE" (list 14950 8120) (list 14950 920) "")
(command "-LAYER" "S" "Cables_UTP" "")
(command "-COLOR" "5")
(command "_.PLINE" (list 14925.0 390) (list 14925.0 400) (list 14925.0 8150) "")
(command "_.LINE" (list 14925.0 8150) (list 14950 8150) "")
(command "_.LINE" (list 14950 8150) (list 14950 4560) "")
(command "_.LINE" (list 14950 8150) (list 14950 2320) "")
(command "_.LINE" (list 14950 8150) (list 14950 5560) "")
(command "_.LINE" (list 14950 8150) (list 14950 6720) "")
(command "_.LINE" (list 14950 8150) (list 14950 7960) "")
(command "_.LINE" (list 14950 8150) (list 14950 3480) "")
(command "_.LINE" (list 14950 8150) (list 14950 1000) "")
(command "-LAYER" "S" "Cables_UTP" "")
(command "-COLOR" "5")
(command "_.PLINE" (list 15975.0 590) (list 15975.0 600) (list 15975.0 8090) "")
(command "_.LINE" (list 15975.0 8090) (list 16000 8090) "")
(command "_.LINE" (list 16000 8090) (list 16000 7800) "")
(command "_.LINE" (list 16000 8090) (list 16000 6560) "")
(command "_.LINE" (list 16000 8090) (list 16000 5400) "")
(command "_.LINE" (list 16000 8090) (list 16000 840) "")
(command "-LAYER" "S" "Cables_UTP" "")
(command "-COLOR" "5")
(command "_.PLINE" (list 15975.0 490) (list 15975.0 500) (list 15975.0 8120) "")
(command "_.LINE" (list 15975.0 8120) (list 16000 8120) "")
(command "_.LINE" (list 16000 8120) (list 16000 7880) "")
(command "_.LINE" (list 16000 8120) (list 16000 6640) "")
(command "_.LINE" (list 16000 8120) (list 16000 5480) "")
(command "_.LINE" (list 16000 8120) (list 16000 920) "")
(command "-LAYER" "S" "Cables_UTP" "")
(command "-COLOR" "5")
(command "_.PLINE" (list 15975.0 390) (list 15975.0 400) (list 15975.0 8150) "")
(command "_.LINE" (list 15975.0 8150) (list 16000 8150) "")
(command "_.LINE" (list 16000 8150) (list 16000 7960) "")
(command "_.LINE" (list 16000 8150) (list 16000 6720) "")
(command "_.LINE" (list 16000 8150) (list 16000 5560) "")
(command "_.LINE" (list 16000 8150) (list 16000 1000) "")
(princ "DONE.")

; === DIBUJAR CABLES DE FIBRA OPTICA (DIAGONAL) ===
(princ "\nDibujando cables de Fibra Optica...")
(command "-LAYER" "S" "Fibra_Data" "")
(command "-COLOR" "2")
(command "_.LINE" (list 300 260.0) (list 1200 170.0) "")
(command "-LAYER" "S" "Textos" "")
(command "-COLOR" "7")
(command "-TEXT" "S" "Standard" "J" "C" (list 750.0 225.0) 10 0 "FO CCTV")
(command "_.LINE" (list 300 260.0) (list 2250 170.0) "")
(command "-LAYER" "S" "Textos" "")
(command "-COLOR" "7")
(command "-TEXT" "S" "Standard" "J" "C" (list 1275.0 225.0) 10 0 "FO CCTV")
(command "_.LINE" (list 300 260.0) (list 3300 170.0) "")
(command "-LAYER" "S" "Textos" "")
(command "-COLOR" "7")
(command "-TEXT" "S" "Standard" "J" "C" (list 1800.0 225.0) 10 0 "FO CCTV")
(command "_.LINE" (list 300 260.0) (list 4350 170.0) "")
(command "-LAYER" "S" "Textos" "")
(command "-COLOR" "7")
(command "-TEXT" "S" "Standard" "J" "C" (list 2325.0 225.0) 10 0 "FO CCTV")
(command "_.LINE" (list 300 260.0) (list 5400 170.0) "")
(command "-LAYER" "S" "Textos" "")
(command "-COLOR" "7")
(command "-TEXT" "S" "Standard" "J" "C" (list 2850.0 225.0) 10 0 "FO CCTV")
(command "_.LINE" (list 300 260.0) (list 6450 170.0) "")
(command "-LAYER" "S" "Textos" "")
(command "-COLOR" "7")
(command "-TEXT" "S" "Standard" "J" "C" (list 3375.0 225.0) 10 0 "FO CCTV")
(command "_.LINE" (list 300 260.0) (list 7500 170.0) "")
(command "-LAYER" "S" "Textos" "")
(command "-COLOR" "7")
(command "-TEXT" "S" "Standard" "J" "C" (list 3900.0 225.0) 10 0 "FO CCTV")
(command "_.LINE" (list 300 260.0) (list 8550 170.0) "")
(command "-LAYER" "S" "Textos" "")
(command "-COLOR" "7")
(command "-TEXT" "S" "Standard" "J" "C" (list 4425.0 225.0) 10 0 "FO CCTV")
(command "_.LINE" (list 300 260.0) (list 9600 170.0) "")
(command "-LAYER" "S" "Textos" "")
(command "-COLOR" "7")
(command "-TEXT" "S" "Standard" "J" "C" (list 4950.0 225.0) 10 0 "FO CCTV")
(command "_.LINE" (list 300 260.0) (list 10650 170.0) "")
(command "-LAYER" "S" "Textos" "")
(command "-COLOR" "7")
(command "-TEXT" "S" "Standard" "J" "C" (list 5475.0 225.0) 10 0 "FO CCTV")
(command "_.LINE" (list 300 260.0) (list 11700 170.0) "")
(command "-LAYER" "S" "Textos" "")
(command "-COLOR" "7")
(command "-TEXT" "S" "Standard" "J" "C" (list 6000.0 225.0) 10 0 "FO CCTV")
(command "_.LINE" (list 300 260.0) (list 12750 170.0) "")
(command "-LAYER" "S" "Textos" "")
(command "-COLOR" "7")
(command "-TEXT" "S" "Standard" "J" "C" (list 6525.0 225.0) 10 0 "FO CCTV")
(command "_.LINE" (list 300 260.0) (list 13800 170.0) "")
(command "-LAYER" "S" "Textos" "")
(command "-COLOR" "7")
(command "-TEXT" "S" "Standard" "J" "C" (list 7050.0 225.0) 10 0 "FO CCTV")
(command "_.LINE" (list 300 260.0) (list 14850 170.0) "")
(command "-LAYER" "S" "Textos" "")
(command "-COLOR" "7")
(command "-TEXT" "S" "Standard" "J" "C" (list 7575.0 225.0) 10 0 "FO CCTV")
(command "_.LINE" (list 300 260.0) (list 15900 170.0) "")
(command "-LAYER" "S" "Textos" "")
(command "-COLOR" "7")
(command "-TEXT" "S" "Standard" "J" "C" (list 8100.0 225.0) 10 0 "FO CCTV")
(command "_.LINE" (list 300 360.0) (list 1200 270.0) "")
(command "-LAYER" "S" "Textos" "")
(command "-COLOR" "7")
(command "-TEXT" "S" "Standard" "J" "C" (list 750.0 325.0) 10 0 "FO DATA")
(command "_.LINE" (list 300 360.0) (list 2250 270.0) "")
(command "-LAYER" "S" "Textos" "")
(command "-COLOR" "7")
(command "-TEXT" "S" "Standard" "J" "C" (list 1275.0 325.0) 10 0 "FO DATA")
(command "_.LINE" (list 300 360.0) (list 3300 270.0) "")
(command "-LAYER" "S" "Textos" "")
(command "-COLOR" "7")
(command "-TEXT" "S" "Standard" "J" "C" (list 1800.0 325.0) 10 0 "FO DATA")
(command "_.LINE" (list 300 360.0) (list 4350 270.0) "")
(command "-LAYER" "S" "Textos" "")
(command "-COLOR" "7")
(command "-TEXT" "S" "Standard" "J" "C" (list 2325.0 325.0) 10 0 "FO DATA")
(command "_.LINE" (list 300 360.0) (list 5400 270.0) "")
(command "-LAYER" "S" "Textos" "")
(command "-COLOR" "7")
(command "-TEXT" "S" "Standard" "J" "C" (list 2850.0 325.0) 10 0 "FO DATA")
(command "_.LINE" (list 300 360.0) (list 6450 270.0) "")
(command "-LAYER" "S" "Textos" "")
(command "-COLOR" "7")
(command "-TEXT" "S" "Standard" "J" "C" (list 3375.0 325.0) 10 0 "FO DATA")
(command "_.LINE" (list 300 360.0) (list 7500 270.0) "")
(command "-LAYER" "S" "Textos" "")
(command "-COLOR" "7")
(command "-TEXT" "S" "Standard" "J" "C" (list 3900.0 325.0) 10 0 "FO DATA")
(command "_.LINE" (list 300 360.0) (list 8550 270.0) "")
(command "-LAYER" "S" "Textos" "")
(command "-COLOR" "7")
(command "-TEXT" "S" "Standard" "J" "C" (list 4425.0 325.0) 10 0 "FO DATA")
(command "_.LINE" (list 300 360.0) (list 9600 270.0) "")
(command "-LAYER" "S" "Textos" "")
(command "-COLOR" "7")
(command "-TEXT" "S" "Standard" "J" "C" (list 4950.0 325.0) 10 0 "FO DATA")
(command "_.LINE" (list 300 360.0) (list 10650 270.0) "")
(command "-LAYER" "S" "Textos" "")
(command "-COLOR" "7")
(command "-TEXT" "S" "Standard" "J" "C" (list 5475.0 325.0) 10 0 "FO DATA")
(command "_.LINE" (list 300 360.0) (list 11700 270.0) "")
(command "-LAYER" "S" "Textos" "")
(command "-COLOR" "7")
(command "-TEXT" "S" "Standard" "J" "C" (list 6000.0 325.0) 10 0 "FO DATA")
(command "_.LINE" (list 300 360.0) (list 12750 270.0) "")
(command "-LAYER" "S" "Textos" "")
(command "-COLOR" "7")
(command "-TEXT" "S" "Standard" "J" "C" (list 6525.0 325.0) 10 0 "FO DATA")
(command "_.LINE" (list 300 360.0) (list 13800 270.0) "")
(command "-LAYER" "S" "Textos" "")
(command "-COLOR" "7")
(command "-TEXT" "S" "Standard" "J" "C" (list 7050.0 325.0) 10 0 "FO DATA")
(command "_.LINE" (list 300 360.0) (list 14850 270.0) "")
(command "-LAYER" "S" "Textos" "")
(command "-COLOR" "7")
(command "-TEXT" "S" "Standard" "J" "C" (list 7575.0 325.0) 10 0 "FO DATA")
(command "_.LINE" (list 300 360.0) (list 15900 270.0) "")
(command "-LAYER" "S" "Textos" "")
(command "-COLOR" "7")
(command "-TEXT" "S" "Standard" "J" "C" (list 8100.0 325.0) 10 0 "FO DATA")
(command "_.LINE" (list 300 460.0) (list 1200 370.0) "")
(command "-LAYER" "S" "Textos" "")
(command "-COLOR" "7")
(command "-TEXT" "S" "Standard" "J" "C" (list 750.0 425.0) 10 0 "FO IPTV")
(command "_.LINE" (list 300 460.0) (list 2250 370.0) "")
(command "-LAYER" "S" "Textos" "")
(command "-COLOR" "7")
(command "-TEXT" "S" "Standard" "J" "C" (list 1275.0 425.0) 10 0 "FO IPTV")
(command "_.LINE" (list 300 460.0) (list 3300 370.0) "")
(command "-LAYER" "S" "Textos" "")
(command "-COLOR" "7")
(command "-TEXT" "S" "Standard" "J" "C" (list 1800.0 425.0) 10 0 "FO IPTV")
(command "_.LINE" (list 300 460.0) (list 4350 370.0) "")
(command "-LAYER" "S" "Textos" "")
(command "-COLOR" "7")
(command "-TEXT" "S" "Standard" "J" "C" (list 2325.0 425.0) 10 0 "FO IPTV")
(command "_.LINE" (list 300 460.0) (list 5400 370.0) "")
(command "-LAYER" "S" "Textos" "")
(command "-COLOR" "7")
(command "-TEXT" "S" "Standard" "J" "C" (list 2850.0 425.0) 10 0 "FO IPTV")
(command "_.LINE" (list 300 460.0) (list 6450 370.0) "")
(command "-LAYER" "S" "Textos" "")
(command "-COLOR" "7")
(command "-TEXT" "S" "Standard" "J" "C" (list 3375.0 425.0) 10 0 "FO IPTV")
(command "_.LINE" (list 300 460.0) (list 7500 370.0) "")
(command "-LAYER" "S" "Textos" "")
(command "-COLOR" "7")
(command "-TEXT" "S" "Standard" "J" "C" (list 3900.0 425.0) 10 0 "FO IPTV")
(command "_.LINE" (list 300 460.0) (list 8550 370.0) "")
(command "-LAYER" "S" "Textos" "")
(command "-COLOR" "7")
(command "-TEXT" "S" "Standard" "J" "C" (list 4425.0 425.0) 10 0 "FO IPTV")
(command "_.LINE" (list 300 460.0) (list 9600 370.0) "")
(command "-LAYER" "S" "Textos" "")
(command "-COLOR" "7")
(command "-TEXT" "S" "Standard" "J" "C" (list 4950.0 425.0) 10 0 "FO IPTV")
(command "_.LINE" (list 300 460.0) (list 10650 370.0) "")
(command "-LAYER" "S" "Textos" "")
(command "-COLOR" "7")
(command "-TEXT" "S" "Standard" "J" "C" (list 5475.0 425.0) 10 0 "FO IPTV")
(command "_.LINE" (list 300 460.0) (list 11700 370.0) "")
(command "-LAYER" "S" "Textos" "")
(command "-COLOR" "7")
(command "-TEXT" "S" "Standard" "J" "C" (list 6000.0 425.0) 10 0 "FO IPTV")
(command "_.LINE" (list 300 460.0) (list 12750 370.0) "")
(command "-LAYER" "S" "Textos" "")
(command "-COLOR" "7")
(command "-TEXT" "S" "Standard" "J" "C" (list 6525.0 425.0) 10 0 "FO IPTV")
(command "_.LINE" (list 300 460.0) (list 13800 370.0) "")
(command "-LAYER" "S" "Textos" "")
(command "-COLOR" "7")
(command "-TEXT" "S" "Standard" "J" "C" (list 7050.0 425.0) 10 0 "FO IPTV")
(command "_.LINE" (list 300 460.0) (list 14850 370.0) "")
(command "-LAYER" "S" "Textos" "")
(command "-COLOR" "7")
(command "-TEXT" "S" "Standard" "J" "C" (list 7575.0 425.0) 10 0 "FO IPTV")
(command "_.LINE" (list 300 460.0) (list 15900 370.0) "")
(command "-LAYER" "S" "Textos" "")
(command "-COLOR" "7")
(command "-TEXT" "S" "Standard" "J" "C" (list 8100.0 425.0) 10 0 "FO IPTV")
(command "_.LINE" (list 300 560.0) (list 1200 470.0) "")
(command "-LAYER" "S" "Textos" "")
(command "-COLOR" "7")
(command "-TEXT" "S" "Standard" "J" "C" (list 750.0 525.0) 10 0 "FO TEL")
(command "_.LINE" (list 300 560.0) (list 2250 470.0) "")
(command "-LAYER" "S" "Textos" "")
(command "-COLOR" "7")
(command "-TEXT" "S" "Standard" "J" "C" (list 1275.0 525.0) 10 0 "FO TEL")
(command "_.LINE" (list 300 560.0) (list 3300 470.0) "")
(command "-LAYER" "S" "Textos" "")
(command "-COLOR" "7")
(command "-TEXT" "S" "Standard" "J" "C" (list 1800.0 525.0) 10 0 "FO TEL")
(command "_.LINE" (list 300 560.0) (list 4350 470.0) "")
(command "-LAYER" "S" "Textos" "")
(command "-COLOR" "7")
(command "-TEXT" "S" "Standard" "J" "C" (list 2325.0 525.0) 10 0 "FO TEL")
(command "_.LINE" (list 300 560.0) (list 5400 470.0) "")
(command "-LAYER" "S" "Textos" "")
(command "-COLOR" "7")
(command "-TEXT" "S" "Standard" "J" "C" (list 2850.0 525.0) 10 0 "FO TEL")
(command "_.LINE" (list 300 560.0) (list 6450 470.0) "")
(command "-LAYER" "S" "Textos" "")
(command "-COLOR" "7")
(command "-TEXT" "S" "Standard" "J" "C" (list 3375.0 525.0) 10 0 "FO TEL")
(command "_.LINE" (list 300 560.0) (list 7500 470.0) "")
(command "-LAYER" "S" "Textos" "")
(command "-COLOR" "7")
(command "-TEXT" "S" "Standard" "J" "C" (list 3900.0 525.0) 10 0 "FO TEL")
(command "_.LINE" (list 300 560.0) (list 8550 470.0) "")
(command "-LAYER" "S" "Textos" "")
(command "-COLOR" "7")
(command "-TEXT" "S" "Standard" "J" "C" (list 4425.0 525.0) 10 0 "FO TEL")
(command "_.LINE" (list 300 560.0) (list 9600 470.0) "")
(command "-LAYER" "S" "Textos" "")
(command "-COLOR" "7")
(command "-TEXT" "S" "Standard" "J" "C" (list 4950.0 525.0) 10 0 "FO TEL")
(command "_.LINE" (list 300 560.0) (list 10650 470.0) "")
(command "-LAYER" "S" "Textos" "")
(command "-COLOR" "7")
(command "-TEXT" "S" "Standard" "J" "C" (list 5475.0 525.0) 10 0 "FO TEL")
(command "_.LINE" (list 300 560.0) (list 11700 470.0) "")
(command "-LAYER" "S" "Textos" "")
(command "-COLOR" "7")
(command "-TEXT" "S" "Standard" "J" "C" (list 6000.0 525.0) 10 0 "FO TEL")
(command "_.LINE" (list 300 560.0) (list 12750 470.0) "")
(command "-LAYER" "S" "Textos" "")
(command "-COLOR" "7")
(command "-TEXT" "S" "Standard" "J" "C" (list 6525.0 525.0) 10 0 "FO TEL")
(command "_.LINE" (list 300 560.0) (list 13800 470.0) "")
(command "-LAYER" "S" "Textos" "")
(command "-COLOR" "7")
(command "-TEXT" "S" "Standard" "J" "C" (list 7050.0 525.0) 10 0 "FO TEL")
(command "_.LINE" (list 300 560.0) (list 14850 470.0) "")
(command "-LAYER" "S" "Textos" "")
(command "-COLOR" "7")
(command "-TEXT" "S" "Standard" "J" "C" (list 7575.0 525.0) 10 0 "FO TEL")
(command "_.LINE" (list 300 560.0) (list 15900 470.0) "")
(command "-LAYER" "S" "Textos" "")
(command "-COLOR" "7")
(command "-TEXT" "S" "Standard" "J" "C" (list 8100.0 525.0) 10 0 "FO TEL")
(command "_.LINE" (list 300 660.0) (list 1200 570.0) "")
(command "-LAYER" "S" "Textos" "")
(command "-COLOR" "7")
(command "-TEXT" "S" "Standard" "J" "C" (list 750.0 625.0) 10 0 "FO WIFI")
(command "_.LINE" (list 300 660.0) (list 2250 570.0) "")
(command "-LAYER" "S" "Textos" "")
(command "-COLOR" "7")
(command "-TEXT" "S" "Standard" "J" "C" (list 1275.0 625.0) 10 0 "FO WIFI")
(command "_.LINE" (list 300 660.0) (list 3300 570.0) "")
(command "-LAYER" "S" "Textos" "")
(command "-COLOR" "7")
(command "-TEXT" "S" "Standard" "J" "C" (list 1800.0 625.0) 10 0 "FO WIFI")
(command "_.LINE" (list 300 660.0) (list 4350 570.0) "")
(command "-LAYER" "S" "Textos" "")
(command "-COLOR" "7")
(command "-TEXT" "S" "Standard" "J" "C" (list 2325.0 625.0) 10 0 "FO WIFI")
(command "_.LINE" (list 300 660.0) (list 5400 570.0) "")
(command "-LAYER" "S" "Textos" "")
(command "-COLOR" "7")
(command "-TEXT" "S" "Standard" "J" "C" (list 2850.0 625.0) 10 0 "FO WIFI")
(command "_.LINE" (list 300 660.0) (list 6450 570.0) "")
(command "-LAYER" "S" "Textos" "")
(command "-COLOR" "7")
(command "-TEXT" "S" "Standard" "J" "C" (list 3375.0 625.0) 10 0 "FO WIFI")
(command "_.LINE" (list 300 660.0) (list 7500 570.0) "")
(command "-LAYER" "S" "Textos" "")
(command "-COLOR" "7")
(command "-TEXT" "S" "Standard" "J" "C" (list 3900.0 625.0) 10 0 "FO WIFI")
(command "_.LINE" (list 300 660.0) (list 8550 570.0) "")
(command "-LAYER" "S" "Textos" "")
(command "-COLOR" "7")
(command "-TEXT" "S" "Standard" "J" "C" (list 4425.0 625.0) 10 0 "FO WIFI")
(command "_.LINE" (list 300 660.0) (list 9600 570.0) "")
(command "-LAYER" "S" "Textos" "")
(command "-COLOR" "7")
(command "-TEXT" "S" "Standard" "J" "C" (list 4950.0 625.0) 10 0 "FO WIFI")
(command "_.LINE" (list 300 660.0) (list 10650 570.0) "")
(command "-LAYER" "S" "Textos" "")
(command "-COLOR" "7")
(command "-TEXT" "S" "Standard" "J" "C" (list 5475.0 625.0) 10 0 "FO WIFI")
(command "_.LINE" (list 300 660.0) (list 11700 570.0) "")
(command "-LAYER" "S" "Textos" "")
(command "-COLOR" "7")
(command "-TEXT" "S" "Standard" "J" "C" (list 6000.0 625.0) 10 0 "FO WIFI")
(command "_.LINE" (list 300 660.0) (list 12750 570.0) "")
(command "-LAYER" "S" "Textos" "")
(command "-COLOR" "7")
(command "-TEXT" "S" "Standard" "J" "C" (list 6525.0 625.0) 10 0 "FO WIFI")
(command "_.LINE" (list 300 660.0) (list 13800 570.0) "")
(command "-LAYER" "S" "Textos" "")
(command "-COLOR" "7")
(command "-TEXT" "S" "Standard" "J" "C" (list 7050.0 625.0) 10 0 "FO WIFI")
(command "_.LINE" (list 300 660.0) (list 14850 570.0) "")
(command "-LAYER" "S" "Textos" "")
(command "-COLOR" "7")
(command "-TEXT" "S" "Standard" "J" "C" (list 7575.0 625.0) 10 0 "FO WIFI")
(command "_.LINE" (list 300 660.0) (list 15900 570.0) "")
(command "-LAYER" "S" "Textos" "")
(command "-COLOR" "7")
(command "-TEXT" "S" "Standard" "J" "C" (list 8100.0 625.0) 10 0 "FO WIFI")
(princ "DONE.")

; === DIBUJAR ALIMENTACION DESDE UPS (DIAGONAL) ===
(princ "\nDibujando alimentacion desde UPS...")
(command "-LAYER" "S" "UPS" "")
(command "-COLOR" "1")
(command "_.LINE" (list 190.0 150) (list 225.0 640) "")
(command "-LAYER" "S" "Textos" "")
(command "-COLOR" "7")
(command "-TEXT" "S" "Standard" "J" "C" (list 207.5 405.0) 10 0 "UPS-PWR")
(command "_.LINE" (list 190.0 150) (list 225.0 540) "")
(command "-LAYER" "S" "Textos" "")
(command "-COLOR" "7")
(command "-TEXT" "S" "Standard" "J" "C" (list 207.5 355.0) 10 0 "UPS-PWR")
(command "_.LINE" (list 190.0 150) (list 225.0 440) "")
(command "-LAYER" "S" "Textos" "")
(command "-COLOR" "7")
(command "-TEXT" "S" "Standard" "J" "C" (list 207.5 305.0) 10 0 "UPS-PWR")
(command "_.LINE" (list 190.0 150) (list 225.0 240) "")
(command "-LAYER" "S" "Textos" "")
(command "-COLOR" "7")
(command "-TEXT" "S" "Standard" "J" "C" (list 207.5 205.0) 10 0 "UPS-PWR")
(command "_.LINE" (list 190.0 150) (list 225.0 340) "")
(command "-LAYER" "S" "Textos" "")
(command "-COLOR" "7")
(command "-TEXT" "S" "Standard" "J" "C" (list 207.5 255.0) 10 0 "UPS-PWR")
(command "_.LINE" (list 190.0 150) (list 1275.0 550) "")
(command "-LAYER" "S" "Textos" "")
(command "-COLOR" "7")
(command "-TEXT" "S" "Standard" "J" "C" (list 732.5 360.0) 10 0 "UPS-PWR")
(command "_.LINE" (list 190.0 150) (list 1275.0 450) "")
(command "-LAYER" "S" "Textos" "")
(command "-COLOR" "7")
(command "-TEXT" "S" "Standard" "J" "C" (list 732.5 310.0) 10 0 "UPS-PWR")
(command "_.LINE" (list 190.0 150) (list 1275.0 350) "")
(command "-LAYER" "S" "Textos" "")
(command "-COLOR" "7")
(command "-TEXT" "S" "Standard" "J" "C" (list 732.5 260.0) 10 0 "UPS-PWR")
(command "_.LINE" (list 190.0 150) (list 1275.0 150) "")
(command "-LAYER" "S" "Textos" "")
(command "-COLOR" "7")
(command "-TEXT" "S" "Standard" "J" "C" (list 732.5 160.0) 10 0 "UPS-PWR")
(command "_.LINE" (list 190.0 150) (list 1275.0 250) "")
(command "-LAYER" "S" "Textos" "")
(command "-COLOR" "7")
(command "-TEXT" "S" "Standard" "J" "C" (list 732.5 210.0) 10 0 "UPS-PWR")
(command "_.LINE" (list 190.0 150) (list 2325.0 550) "")
(command "-LAYER" "S" "Textos" "")
(command "-COLOR" "7")
(command "-TEXT" "S" "Standard" "J" "C" (list 1257.5 360.0) 10 0 "UPS-PWR")
(command "_.LINE" (list 190.0 150) (list 2325.0 450) "")
(command "-LAYER" "S" "Textos" "")
(command "-COLOR" "7")
(command "-TEXT" "S" "Standard" "J" "C" (list 1257.5 310.0) 10 0 "UPS-PWR")
(command "_.LINE" (list 190.0 150) (list 2325.0 350) "")
(command "-LAYER" "S" "Textos" "")
(command "-COLOR" "7")
(command "-TEXT" "S" "Standard" "J" "C" (list 1257.5 260.0) 10 0 "UPS-PWR")
(command "_.LINE" (list 190.0 150) (list 2325.0 150) "")
(command "-LAYER" "S" "Textos" "")
(command "-COLOR" "7")
(command "-TEXT" "S" "Standard" "J" "C" (list 1257.5 160.0) 10 0 "UPS-PWR")
(command "_.LINE" (list 190.0 150) (list 2325.0 250) "")
(command "-LAYER" "S" "Textos" "")
(command "-COLOR" "7")
(command "-TEXT" "S" "Standard" "J" "C" (list 1257.5 210.0) 10 0 "UPS-PWR")
(command "_.LINE" (list 190.0 150) (list 3375.0 550) "")
(command "-LAYER" "S" "Textos" "")
(command "-COLOR" "7")
(command "-TEXT" "S" "Standard" "J" "C" (list 1782.5 360.0) 10 0 "UPS-PWR")
(command "_.LINE" (list 190.0 150) (list 3375.0 450) "")
(command "-LAYER" "S" "Textos" "")
(command "-COLOR" "7")
(command "-TEXT" "S" "Standard" "J" "C" (list 1782.5 310.0) 10 0 "UPS-PWR")
(command "_.LINE" (list 190.0 150) (list 3375.0 350) "")
(command "-LAYER" "S" "Textos" "")
(command "-COLOR" "7")
(command "-TEXT" "S" "Standard" "J" "C" (list 1782.5 260.0) 10 0 "UPS-PWR")
(command "_.LINE" (list 190.0 150) (list 3375.0 150) "")
(command "-LAYER" "S" "Textos" "")
(command "-COLOR" "7")
(command "-TEXT" "S" "Standard" "J" "C" (list 1782.5 160.0) 10 0 "UPS-PWR")
(command "_.LINE" (list 190.0 150) (list 3375.0 250) "")
(command "-LAYER" "S" "Textos" "")
(command "-COLOR" "7")
(command "-TEXT" "S" "Standard" "J" "C" (list 1782.5 210.0) 10 0 "UPS-PWR")
(command "_.LINE" (list 190.0 150) (list 4425.0 550) "")
(command "-LAYER" "S" "Textos" "")
(command "-COLOR" "7")
(command "-TEXT" "S" "Standard" "J" "C" (list 2307.5 360.0) 10 0 "UPS-PWR")
(command "_.LINE" (list 190.0 150) (list 4425.0 450) "")
(command "-LAYER" "S" "Textos" "")
(command "-COLOR" "7")
(command "-TEXT" "S" "Standard" "J" "C" (list 2307.5 310.0) 10 0 "UPS-PWR")
(command "_.LINE" (list 190.0 150) (list 4425.0 350) "")
(command "-LAYER" "S" "Textos" "")
(command "-COLOR" "7")
(command "-TEXT" "S" "Standard" "J" "C" (list 2307.5 260.0) 10 0 "UPS-PWR")
(command "_.LINE" (list 190.0 150) (list 4425.0 150) "")
(command "-LAYER" "S" "Textos" "")
(command "-COLOR" "7")
(command "-TEXT" "S" "Standard" "J" "C" (list 2307.5 160.0) 10 0 "UPS-PWR")
(command "_.LINE" (list 190.0 150) (list 4425.0 250) "")
(command "-LAYER" "S" "Textos" "")
(command "-COLOR" "7")
(command "-TEXT" "S" "Standard" "J" "C" (list 2307.5 210.0) 10 0 "UPS-PWR")
(command "_.LINE" (list 190.0 150) (list 5475.0 550) "")
(command "-LAYER" "S" "Textos" "")
(command "-COLOR" "7")
(command "-TEXT" "S" "Standard" "J" "C" (list 2832.5 360.0) 10 0 "UPS-PWR")
(command "_.LINE" (list 190.0 150) (list 5475.0 450) "")
(command "-LAYER" "S" "Textos" "")
(command "-COLOR" "7")
(command "-TEXT" "S" "Standard" "J" "C" (list 2832.5 310.0) 10 0 "UPS-PWR")
(command "_.LINE" (list 190.0 150) (list 5475.0 350) "")
(command "-LAYER" "S" "Textos" "")
(command "-COLOR" "7")
(command "-TEXT" "S" "Standard" "J" "C" (list 2832.5 260.0) 10 0 "UPS-PWR")
(command "_.LINE" (list 190.0 150) (list 5475.0 150) "")
(command "-LAYER" "S" "Textos" "")
(command "-COLOR" "7")
(command "-TEXT" "S" "Standard" "J" "C" (list 2832.5 160.0) 10 0 "UPS-PWR")
(command "_.LINE" (list 190.0 150) (list 5475.0 250) "")
(command "-LAYER" "S" "Textos" "")
(command "-COLOR" "7")
(command "-TEXT" "S" "Standard" "J" "C" (list 2832.5 210.0) 10 0 "UPS-PWR")
(command "_.LINE" (list 190.0 150) (list 6525.0 550) "")
(command "-LAYER" "S" "Textos" "")
(command "-COLOR" "7")
(command "-TEXT" "S" "Standard" "J" "C" (list 3357.5 360.0) 10 0 "UPS-PWR")
(command "_.LINE" (list 190.0 150) (list 6525.0 450) "")
(command "-LAYER" "S" "Textos" "")
(command "-COLOR" "7")
(command "-TEXT" "S" "Standard" "J" "C" (list 3357.5 310.0) 10 0 "UPS-PWR")
(command "_.LINE" (list 190.0 150) (list 6525.0 350) "")
(command "-LAYER" "S" "Textos" "")
(command "-COLOR" "7")
(command "-TEXT" "S" "Standard" "J" "C" (list 3357.5 260.0) 10 0 "UPS-PWR")
(command "_.LINE" (list 190.0 150) (list 6525.0 150) "")
(command "-LAYER" "S" "Textos" "")
(command "-COLOR" "7")
(command "-TEXT" "S" "Standard" "J" "C" (list 3357.5 160.0) 10 0 "UPS-PWR")
(command "_.LINE" (list 190.0 150) (list 6525.0 250) "")
(command "-LAYER" "S" "Textos" "")
(command "-COLOR" "7")
(command "-TEXT" "S" "Standard" "J" "C" (list 3357.5 210.0) 10 0 "UPS-PWR")
(command "_.LINE" (list 190.0 150) (list 7575.0 550) "")
(command "-LAYER" "S" "Textos" "")
(command "-COLOR" "7")
(command "-TEXT" "S" "Standard" "J" "C" (list 3882.5 360.0) 10 0 "UPS-PWR")
(command "_.LINE" (list 190.0 150) (list 7575.0 450) "")
(command "-LAYER" "S" "Textos" "")
(command "-COLOR" "7")
(command "-TEXT" "S" "Standard" "J" "C" (list 3882.5 310.0) 10 0 "UPS-PWR")
(command "_.LINE" (list 190.0 150) (list 7575.0 350) "")
(command "-LAYER" "S" "Textos" "")
(command "-COLOR" "7")
(command "-TEXT" "S" "Standard" "J" "C" (list 3882.5 260.0) 10 0 "UPS-PWR")
(command "_.LINE" (list 190.0 150) (list 7575.0 150) "")
(command "-LAYER" "S" "Textos" "")
(command "-COLOR" "7")
(command "-TEXT" "S" "Standard" "J" "C" (list 3882.5 160.0) 10 0 "UPS-PWR")
(command "_.LINE" (list 190.0 150) (list 7575.0 250) "")
(command "-LAYER" "S" "Textos" "")
(command "-COLOR" "7")
(command "-TEXT" "S" "Standard" "J" "C" (list 3882.5 210.0) 10 0 "UPS-PWR")
(command "_.LINE" (list 190.0 150) (list 8625.0 550) "")
(command "-LAYER" "S" "Textos" "")
(command "-COLOR" "7")
(command "-TEXT" "S" "Standard" "J" "C" (list 4407.5 360.0) 10 0 "UPS-PWR")
(command "_.LINE" (list 190.0 150) (list 8625.0 450) "")
(command "-LAYER" "S" "Textos" "")
(command "-COLOR" "7")
(command "-TEXT" "S" "Standard" "J" "C" (list 4407.5 310.0) 10 0 "UPS-PWR")
(command "_.LINE" (list 190.0 150) (list 8625.0 350) "")
(command "-LAYER" "S" "Textos" "")
(command "-COLOR" "7")
(command "-TEXT" "S" "Standard" "J" "C" (list 4407.5 260.0) 10 0 "UPS-PWR")
(command "_.LINE" (list 190.0 150) (list 8625.0 150) "")
(command "-LAYER" "S" "Textos" "")
(command "-COLOR" "7")
(command "-TEXT" "S" "Standard" "J" "C" (list 4407.5 160.0) 10 0 "UPS-PWR")
(command "_.LINE" (list 190.0 150) (list 8625.0 250) "")
(command "-LAYER" "S" "Textos" "")
(command "-COLOR" "7")
(command "-TEXT" "S" "Standard" "J" "C" (list 4407.5 210.0) 10 0 "UPS-PWR")
(command "_.LINE" (list 190.0 150) (list 9675.0 550) "")
(command "-LAYER" "S" "Textos" "")
(command "-COLOR" "7")
(command "-TEXT" "S" "Standard" "J" "C" (list 4932.5 360.0) 10 0 "UPS-PWR")
(command "_.LINE" (list 190.0 150) (list 9675.0 450) "")
(command "-LAYER" "S" "Textos" "")
(command "-COLOR" "7")
(command "-TEXT" "S" "Standard" "J" "C" (list 4932.5 310.0) 10 0 "UPS-PWR")
(command "_.LINE" (list 190.0 150) (list 9675.0 350) "")
(command "-LAYER" "S" "Textos" "")
(command "-COLOR" "7")
(command "-TEXT" "S" "Standard" "J" "C" (list 4932.5 260.0) 10 0 "UPS-PWR")
(command "_.LINE" (list 190.0 150) (list 9675.0 150) "")
(command "-LAYER" "S" "Textos" "")
(command "-COLOR" "7")
(command "-TEXT" "S" "Standard" "J" "C" (list 4932.5 160.0) 10 0 "UPS-PWR")
(command "_.LINE" (list 190.0 150) (list 9675.0 250) "")
(command "-LAYER" "S" "Textos" "")
(command "-COLOR" "7")
(command "-TEXT" "S" "Standard" "J" "C" (list 4932.5 210.0) 10 0 "UPS-PWR")
(command "_.LINE" (list 190.0 150) (list 10725.0 550) "")
(command "-LAYER" "S" "Textos" "")
(command "-COLOR" "7")
(command "-TEXT" "S" "Standard" "J" "C" (list 5457.5 360.0) 10 0 "UPS-PWR")
(command "_.LINE" (list 190.0 150) (list 10725.0 450) "")
(command "-LAYER" "S" "Textos" "")
(command "-COLOR" "7")
(command "-TEXT" "S" "Standard" "J" "C" (list 5457.5 310.0) 10 0 "UPS-PWR")
(command "_.LINE" (list 190.0 150) (list 10725.0 350) "")
(command "-LAYER" "S" "Textos" "")
(command "-COLOR" "7")
(command "-TEXT" "S" "Standard" "J" "C" (list 5457.5 260.0) 10 0 "UPS-PWR")
(command "_.LINE" (list 190.0 150) (list 10725.0 150) "")
(command "-LAYER" "S" "Textos" "")
(command "-COLOR" "7")
(command "-TEXT" "S" "Standard" "J" "C" (list 5457.5 160.0) 10 0 "UPS-PWR")
(command "_.LINE" (list 190.0 150) (list 10725.0 250) "")
(command "-LAYER" "S" "Textos" "")
(command "-COLOR" "7")
(command "-TEXT" "S" "Standard" "J" "C" (list 5457.5 210.0) 10 0 "UPS-PWR")
(command "_.LINE" (list 190.0 150) (list 11775.0 550) "")
(command "-LAYER" "S" "Textos" "")
(command "-COLOR" "7")
(command "-TEXT" "S" "Standard" "J" "C" (list 5982.5 360.0) 10 0 "UPS-PWR")
(command "_.LINE" (list 190.0 150) (list 11775.0 450) "")
(command "-LAYER" "S" "Textos" "")
(command "-COLOR" "7")
(command "-TEXT" "S" "Standard" "J" "C" (list 5982.5 310.0) 10 0 "UPS-PWR")
(command "_.LINE" (list 190.0 150) (list 11775.0 350) "")
(command "-LAYER" "S" "Textos" "")
(command "-COLOR" "7")
(command "-TEXT" "S" "Standard" "J" "C" (list 5982.5 260.0) 10 0 "UPS-PWR")
(command "_.LINE" (list 190.0 150) (list 11775.0 150) "")
(command "-LAYER" "S" "Textos" "")
(command "-COLOR" "7")
(command "-TEXT" "S" "Standard" "J" "C" (list 5982.5 160.0) 10 0 "UPS-PWR")
(command "_.LINE" (list 190.0 150) (list 11775.0 250) "")
(command "-LAYER" "S" "Textos" "")
(command "-COLOR" "7")
(command "-TEXT" "S" "Standard" "J" "C" (list 5982.5 210.0) 10 0 "UPS-PWR")
(command "_.LINE" (list 190.0 150) (list 12825.0 550) "")
(command "-LAYER" "S" "Textos" "")
(command "-COLOR" "7")
(command "-TEXT" "S" "Standard" "J" "C" (list 6507.5 360.0) 10 0 "UPS-PWR")
(command "_.LINE" (list 190.0 150) (list 12825.0 450) "")
(command "-LAYER" "S" "Textos" "")
(command "-COLOR" "7")
(command "-TEXT" "S" "Standard" "J" "C" (list 6507.5 310.0) 10 0 "UPS-PWR")
(command "_.LINE" (list 190.0 150) (list 12825.0 350) "")
(command "-LAYER" "S" "Textos" "")
(command "-COLOR" "7")
(command "-TEXT" "S" "Standard" "J" "C" (list 6507.5 260.0) 10 0 "UPS-PWR")
(command "_.LINE" (list 190.0 150) (list 12825.0 150) "")
(command "-LAYER" "S" "Textos" "")
(command "-COLOR" "7")
(command "-TEXT" "S" "Standard" "J" "C" (list 6507.5 160.0) 10 0 "UPS-PWR")
(command "_.LINE" (list 190.0 150) (list 12825.0 250) "")
(command "-LAYER" "S" "Textos" "")
(command "-COLOR" "7")
(command "-TEXT" "S" "Standard" "J" "C" (list 6507.5 210.0) 10 0 "UPS-PWR")
(command "_.LINE" (list 190.0 150) (list 13875.0 550) "")
(command "-LAYER" "S" "Textos" "")
(command "-COLOR" "7")
(command "-TEXT" "S" "Standard" "J" "C" (list 7032.5 360.0) 10 0 "UPS-PWR")
(command "_.LINE" (list 190.0 150) (list 13875.0 450) "")
(command "-LAYER" "S" "Textos" "")
(command "-COLOR" "7")
(command "-TEXT" "S" "Standard" "J" "C" (list 7032.5 310.0) 10 0 "UPS-PWR")
(command "_.LINE" (list 190.0 150) (list 13875.0 350) "")
(command "-LAYER" "S" "Textos" "")
(command "-COLOR" "7")
(command "-TEXT" "S" "Standard" "J" "C" (list 7032.5 260.0) 10 0 "UPS-PWR")
(command "_.LINE" (list 190.0 150) (list 13875.0 150) "")
(command "-LAYER" "S" "Textos" "")
(command "-COLOR" "7")
(command "-TEXT" "S" "Standard" "J" "C" (list 7032.5 160.0) 10 0 "UPS-PWR")
(command "_.LINE" (list 190.0 150) (list 13875.0 250) "")
(command "-LAYER" "S" "Textos" "")
(command "-COLOR" "7")
(command "-TEXT" "S" "Standard" "J" "C" (list 7032.5 210.0) 10 0 "UPS-PWR")
(command "_.LINE" (list 190.0 150) (list 14925.0 550) "")
(command "-LAYER" "S" "Textos" "")
(command "-COLOR" "7")
(command "-TEXT" "S" "Standard" "J" "C" (list 7557.5 360.0) 10 0 "UPS-PWR")
(command "_.LINE" (list 190.0 150) (list 14925.0 450) "")
(command "-LAYER" "S" "Textos" "")
(command "-COLOR" "7")
(command "-TEXT" "S" "Standard" "J" "C" (list 7557.5 310.0) 10 0 "UPS-PWR")
(command "_.LINE" (list 190.0 150) (list 14925.0 350) "")
(command "-LAYER" "S" "Textos" "")
(command "-COLOR" "7")
(command "-TEXT" "S" "Standard" "J" "C" (list 7557.5 260.0) 10 0 "UPS-PWR")
(command "_.LINE" (list 190.0 150) (list 14925.0 150) "")
(command "-LAYER" "S" "Textos" "")
(command "-COLOR" "7")
(command "-TEXT" "S" "Standard" "J" "C" (list 7557.5 160.0) 10 0 "UPS-PWR")
(command "_.LINE" (list 190.0 150) (list 14925.0 250) "")
(command "-LAYER" "S" "Textos" "")
(command "-COLOR" "7")
(command "-TEXT" "S" "Standard" "J" "C" (list 7557.5 210.0) 10 0 "UPS-PWR")
(command "_.LINE" (list 190.0 150) (list 15975.0 550) "")
(command "-LAYER" "S" "Textos" "")
(command "-COLOR" "7")
(command "-TEXT" "S" "Standard" "J" "C" (list 8082.5 360.0) 10 0 "UPS-PWR")
(command "_.LINE" (list 190.0 150) (list 15975.0 450) "")
(command "-LAYER" "S" "Textos" "")
(command "-COLOR" "7")
(command "-TEXT" "S" "Standard" "J" "C" (list 8082.5 310.0) 10 0 "UPS-PWR")
(command "_.LINE" (list 190.0 150) (list 15975.0 350) "")
(command "-LAYER" "S" "Textos" "")
(command "-COLOR" "7")
(command "-TEXT" "S" "Standard" "J" "C" (list 8082.5 260.0) 10 0 "UPS-PWR")
(command "_.LINE" (list 190.0 150) (list 15975.0 150) "")
(command "-LAYER" "S" "Textos" "")
(command "-COLOR" "7")
(command "-TEXT" "S" "Standard" "J" "C" (list 8082.5 160.0) 10 0 "UPS-PWR")
(command "_.LINE" (list 190.0 150) (list 15975.0 250) "")
(command "-LAYER" "S" "Textos" "")
(command "-COLOR" "7")
(command "-TEXT" "S" "Standard" "J" "C" (list 8082.5 210.0) 10 0 "UPS-PWR")
(princ "DONE.")

; === FINALIZAR DIBUJO ===
(command "_.ZOOM" "E")
(command "_.UNDO" "END")
